TEGILE-MIB DEFINITIONS ::= BEGIN

IMPORTS
    MODULE-IDENTITY, 
    OBJECT-TYPE, 
    NOTIFICATION-TYPE,
    Counter64, 
    Unsigned32, 
    enterprises, 
    IpAddress
        FROM SNMPv2-SMI
    DisplayString, TruthValue
        FROM SNMPv2-TC
    MODULE-COMPLIANCE, OBJECT-GROUP, NOTIFICATION-GROUP
        FROM SNMPv2-CONF;

tegile MODULE-IDENTITY
    LAST-UPDATED    "201802281010Z"
    ORGANIZATION    "Tegile Storage, Inc."
    CONTACT-INFO    "support@tegile.com"
    DESCRIPTION     "Tegile SNMP Definition"

    REVISION        "201802281010Z"
    DESCRIPTION     "Tegile Storage 2.0.0.1 MIB.
                     Rearranged the objects in new object groups, making older object group 
                     obsolete.
                     Disk related analytics and global cache analytics are no longer provided.
                     Related OIDs are made obsolete now.
                     Throughput data is now displayed in MiB/s.
                     Added new notification for share modification event."

    REVISION        "201707041010Z"
    DESCRIPTION     "Tegile Storage 2.0.0.0 MIB. 
                     Added 64 Bit support.
                     Added new tables for HyperV SMB VM, Interface Group, Link Aggregate, 
                     Mapped Interfaces and Physical Interfaces.
                     Changed the indexing for Disk Objects.
                     Added some new notifications."
                     
    REVISION        "201609101010Z"
    DESCRIPTION     "Tegile Storage 1.0.0.2 MIB. Added NVDIMM specific notifications"

    REVISION        "201604061010Z"
    DESCRIPTION     "Tegile Storage 1.0.0.1 MIB. Added traps for Disk Slow IO and Login failures"

    REVISION        "201509231010Z"
    DESCRIPTION     "Tegile Storage 1.0.0.0 MIB"
    ::= { enterprises 43906 }

--
-- Tegile Objects (variables and tables)
--

tegileArray                         OBJECT IDENTIFIER ::= { tegile 1 }
tegileArray-notifications           OBJECT IDENTIFIER ::= { tegile 2 }

properties                          OBJECT IDENTIFIER ::= { tegileArray 1 }
globalStatistics                    OBJECT IDENTIFIER ::= { tegileArray 2 }
disks                               OBJECT IDENTIFIER ::= { tegileArray 3 }
pools                               OBJECT IDENTIFIER ::= { tegileArray 4 }
network                             OBJECT IDENTIFIER ::= { tegileArray 5 }
sanProperties                       OBJECT IDENTIFIER ::= { tegileArray 6 }
vmwareNFSDatastores                 OBJECT IDENTIFIER ::= { tegileArray 7 }
hypervSMBVMs                        OBJECT IDENTIFIER ::= { tegileArray 8 }
haResources                         OBJECT IDENTIFIER ::= { tegileArray 9 }

poolProjects                        OBJECT IDENTIFIER ::= { pools 3 }

projectLUNs                         OBJECT IDENTIFIER ::= { poolProjects 2 }
projectShares                       OBJECT IDENTIFIER ::= { poolProjects 3 }

networkInterfaces                   OBJECT IDENTIFIER ::= { network 1 }
linkAggregates                      OBJECT IDENTIFIER ::= { network 2 }
interfaceGroups                     OBJECT IDENTIFIER ::= { network 3 }

mappedInterfaces                    OBJECT IDENTIFIER ::= { interfaceGroups 2 }
physicalInterfaces                  OBJECT IDENTIFIER ::= { interfaceGroups 3 }

iscsiProperties                     OBJECT IDENTIFIER ::= { sanProperties 1 }
fcProperties                        OBJECT IDENTIFIER ::= { sanProperties 2 }

iscsiTargets                        OBJECT IDENTIFIER ::= { iscsiProperties 1 }
iscsiInitiators                     OBJECT IDENTIFIER ::= { iscsiProperties 2 }

fcTargets                           OBJECT IDENTIFIER ::= { fcProperties 1 }
fcInitiators                        OBJECT IDENTIFIER ::= { fcProperties 2 }

--
-- Properties
--
arrayHostName OBJECT-TYPE
    SYNTAX         OCTET STRING
    MAX-ACCESS     read-only
    STATUS         current
    DESCRIPTION
    "Array host name"
    ::= { properties 1 }

arrayManagementIP OBJECT-TYPE
    SYNTAX         IpAddress
    MAX-ACCESS     read-only
    STATUS         current
    DESCRIPTION
    "Array management IP"
    ::= { properties 2 }

arrayHardwareModel OBJECT-TYPE
    SYNTAX         OCTET STRING
    MAX-ACCESS     read-only
    STATUS         current
    DESCRIPTION
    "Array Hardware model number"
    ::= { properties 3 }

arraySoftwareVersion OBJECT-TYPE
    SYNTAX         OCTET STRING
    MAX-ACCESS     read-only
    STATUS         current
    DESCRIPTION
    "Array Software version"
    ::= { properties 4 }

arrayGUID OBJECT-TYPE
    SYNTAX         OCTET STRING
    MAX-ACCESS     read-only
    STATUS         current
    DESCRIPTION
    "Array GUID"
    ::= { properties 5 }

haControllerA-Name OBJECT-TYPE
    SYNTAX         OCTET STRING
    MAX-ACCESS     read-only
    STATUS         current
    DESCRIPTION
    "HA Controller A Name"
    ::= { properties 6 }

haControllerA-IPAddr OBJECT-TYPE
    SYNTAX         IpAddress
    MAX-ACCESS     read-only
    STATUS         current
    DESCRIPTION
    "HA Controller A IP address"
    ::= { properties 7 }

haControllerA-Uptime OBJECT-TYPE
    SYNTAX         OCTET STRING
    MAX-ACCESS     read-only
    STATUS         current
    DESCRIPTION
    "HA Controller A uptime"
    ::= { properties 8 }

haControllerB-Name OBJECT-TYPE
    SYNTAX         OCTET STRING
    MAX-ACCESS     read-only
    STATUS         current
    DESCRIPTION
    "HA Controller B Name"
    ::= { properties 9 }

haControllerB-IPAddr OBJECT-TYPE
    SYNTAX         IpAddress
    MAX-ACCESS     read-only
    STATUS         current
    DESCRIPTION
    "HA Controller B IP address"
    ::= { properties 10 }

haControllerB-Uptime OBJECT-TYPE
    SYNTAX         OCTET STRING
    MAX-ACCESS     read-only
    STATUS         current
    DESCRIPTION
    "HA Controller B uptime"
    ::= { properties 11 }
    
snmpAgentVersion OBJECT-TYPE
    SYNTAX         OCTET STRING
    MAX-ACCESS     read-only
    STATUS         current
    DESCRIPTION
    "Tegile SNMP agent version"
    ::= { properties 12 }

--
-- Global Statistics
--
-- CPU  Stats
--
cpuTotalUsage OBJECT-TYPE
    SYNTAX         Unsigned32
    MAX-ACCESS     read-only
    STATUS         current
    DESCRIPTION
    "Total CPU usage"
    ::= { globalStatistics 1 }

cpuSystemCalls OBJECT-TYPE
    SYNTAX         Unsigned32
    MAX-ACCESS     read-only
    STATUS         current
    DESCRIPTION
    "Number of system calls"
    ::= { globalStatistics 2 }

cpuInterrupts OBJECT-TYPE
    SYNTAX         Unsigned32
    MAX-ACCESS     read-only
    STATUS         current
    DESCRIPTION
    "Number of CPU interrupts"
    ::= { globalStatistics 3 }

--
-- Cache  Stats
--
cacheTotalWriteMbps OBJECT-TYPE
    SYNTAX         Unsigned32
    MAX-ACCESS     read-only
    STATUS         obsolete
    DESCRIPTION
    "OBSOLETE: Cache writes, MBs per second"
    ::= { globalStatistics 4 }

cacheTotalReadMbps OBJECT-TYPE
    SYNTAX         Unsigned32
    MAX-ACCESS     read-only
    STATUS         obsolete
    DESCRIPTION
    "OBSOLETE: Cache reads, MBs per second"
    ::= { globalStatistics 5 }

cacheTotalWriteIops OBJECT-TYPE
    SYNTAX         Unsigned32
    MAX-ACCESS     read-only
    STATUS         obsolete
    DESCRIPTION
    "OBSOLETE: Cache reads, IOs per second"
    ::= { globalStatistics 6 }

cacheTotalReadIops OBJECT-TYPE
    SYNTAX         Unsigned32
    MAX-ACCESS     read-only
    STATUS         obsolete
    DESCRIPTION
    "OBSOLETE: Cache reads, IOs per second"
    ::= { globalStatistics 7 }

cacheRAMReads OBJECT-TYPE
    SYNTAX         Unsigned32
    MAX-ACCESS     read-only
    STATUS         obsolete
    DESCRIPTION
    "OBSOLETE: Cache RAM reads"
    ::= { globalStatistics 8 }

cacheSSDReads OBJECT-TYPE
    SYNTAX         Unsigned32
    MAX-ACCESS     read-only
    STATUS         obsolete
    DESCRIPTION
    "OBSOLETE: Cache SSD reads"
    ::= { globalStatistics 9 }

--
-- Disk  Stats
--
diskTotalWriteMbps OBJECT-TYPE
    SYNTAX         Unsigned32
    MAX-ACCESS     read-only
    STATUS         obsolete
    DESCRIPTION
    "OBSOLETE: Disk writes, MBs per second"
    ::= { globalStatistics 10 }

diskTotalReadMbps OBJECT-TYPE
    SYNTAX         Unsigned32
    MAX-ACCESS     read-only
    STATUS         obsolete
    DESCRIPTION
    "OBSOLETE: Disk reads, MBs per second"
    ::= { globalStatistics 11 }

diskTotalWriteIops OBJECT-TYPE
    SYNTAX         Unsigned32
    MAX-ACCESS     read-only
    STATUS         obsolete
    DESCRIPTION
    "OBSOLETE: Disk writes, IOs per second"
    ::= { globalStatistics 12 }

diskTotalReadIops OBJECT-TYPE
    SYNTAX         Unsigned32
    MAX-ACCESS     read-only
    STATUS         obsolete
    DESCRIPTION
    "OBSOLETE: Disk reads, IOs per second"
    ::= { globalStatistics 13 }

diskDataWriteMbps OBJECT-TYPE
    SYNTAX         Unsigned32
    MAX-ACCESS     read-only
    STATUS         obsolete
    DESCRIPTION
    "OBSOLETE: Disk data writes, MBs per second"
    ::= { globalStatistics 14 }

diskDataReadMbps OBJECT-TYPE
    SYNTAX         Unsigned32
    MAX-ACCESS     read-only
    STATUS         obsolete
    DESCRIPTION
    "OBSOLETE: Disk data reads, MBs per second"
    ::= { globalStatistics 15 }
    
diskDataWriteIops OBJECT-TYPE
    SYNTAX         Unsigned32
    MAX-ACCESS     read-only
    STATUS         obsolete
    DESCRIPTION
    "OBSOLETE: Disk data writes, IOs per second"
    ::= { globalStatistics 16 }

diskDataReadIops OBJECT-TYPE
    SYNTAX         Unsigned32
    MAX-ACCESS     read-only
    STATUS         obsolete
    DESCRIPTION
    "OBSOLETE: Disk data reads, IOs per second"
    ::= { globalStatistics 17 }

diskAvgWriteLatency OBJECT-TYPE
    SYNTAX         Unsigned32
    MAX-ACCESS     read-only
    STATUS         obsolete
    DESCRIPTION
    "OBSOLETE: Disk average write latency"
    ::= { globalStatistics 18 }

diskAvgReadLatency OBJECT-TYPE
    SYNTAX         Unsigned32
    MAX-ACCESS     read-only
    STATUS         obsolete
    DESCRIPTION
    "OBSOLETE: Disk average read latency"
    ::= { globalStatistics 19 }

diskIOCount OBJECT-TYPE
    SYNTAX         Unsigned32
    MAX-ACCESS     read-only
    STATUS         obsolete
    DESCRIPTION
    "OBSOLETE: Disk total io count"
    ::= { globalStatistics 20 }

diskRandomIOCount OBJECT-TYPE
    SYNTAX         Unsigned32
    MAX-ACCESS     read-only
    STATUS         obsolete
    DESCRIPTION
    "OBSOLETE: Disk random io count"
    ::= { globalStatistics 21 }

diskSequentialIOCount OBJECT-TYPE
    SYNTAX         Unsigned32
    MAX-ACCESS     read-only
    STATUS         obsolete
    DESCRIPTION
    "OBSOLETE: Disk sequential io count"
    ::= { globalStatistics 22 }

--
-- Pool Stats
--
poolTotalWriteMbps OBJECT-TYPE
    SYNTAX         Unsigned32
    MAX-ACCESS     read-only
    STATUS         current
    DESCRIPTION
    "Pool writes, MiBs per second"
    ::= { globalStatistics 23 }

poolTotalReadMbps OBJECT-TYPE
    SYNTAX         Unsigned32
    MAX-ACCESS     read-only
    STATUS         current
    DESCRIPTION
    "Pool reads, MiBs per second"
    ::= { globalStatistics 24 }

poolTotalWriteIops OBJECT-TYPE
    SYNTAX         Unsigned32
    MAX-ACCESS     read-only
    STATUS         current
    DESCRIPTION
    "Pool reads, IOs per second"
    ::= { globalStatistics 25 }

poolTotalReadIops OBJECT-TYPE
    SYNTAX         Unsigned32
    MAX-ACCESS     read-only
    STATUS         current
    DESCRIPTION
    "Pool reads, IOs per second"
    ::= { globalStatistics 26 }

poolAvgWriteLatency OBJECT-TYPE
    SYNTAX         Unsigned32
    MAX-ACCESS     read-only
    STATUS         current
    DESCRIPTION
    "Pool average write latency in milliseconds"
    ::= { globalStatistics 27 }

poolAvgReadLatency OBJECT-TYPE
    SYNTAX         Unsigned32
    MAX-ACCESS     read-only
    STATUS         current
    DESCRIPTION
    "Pool average read latency in milliseconds"
    ::= { globalStatistics 28 }

--
-- CIFS Stats
--
cifsTotalWriteMBps OBJECT-TYPE
    SYNTAX         Unsigned32
    MAX-ACCESS     read-only
    STATUS         current
    DESCRIPTION
    "CIFS writes, MiBs per second"
    ::= { globalStatistics 29 }

cifsTotalReadMBps OBJECT-TYPE
    SYNTAX         Unsigned32
    MAX-ACCESS     read-only
    STATUS         current
    DESCRIPTION
    "CIFS reads, MiBs per second"
    ::= { globalStatistics 30 }

cifsTotalWriteIops OBJECT-TYPE
    SYNTAX         Unsigned32
    MAX-ACCESS     read-only
    STATUS         current
    DESCRIPTION
    "CIFS reads, IOs per second"
    ::= { globalStatistics 31 }

cifsTotalReadIops OBJECT-TYPE
    SYNTAX         Unsigned32
    MAX-ACCESS     read-only
    STATUS         current
    DESCRIPTION
    "CIFS reads, IOs per second"
    ::= { globalStatistics 32 }

cifsAvgWriteLatency OBJECT-TYPE
    SYNTAX         Unsigned32
    MAX-ACCESS     read-only
    STATUS         current
    DESCRIPTION
    "CIFS average write latency in milliseconds"
    ::= { globalStatistics 33 }

cifsAvgReadLatency OBJECT-TYPE
    SYNTAX         Unsigned32
    MAX-ACCESS     read-only
    STATUS         current
    DESCRIPTION
    "CIFS average read latency in milliseconds"
    ::= { globalStatistics 34 }

--
-- NFS Stats
--
nfsTotalWriteMBps OBJECT-TYPE
    SYNTAX         Unsigned32
    MAX-ACCESS     read-only
    STATUS         current
    DESCRIPTION
    "NFS writes, MiBs per second"
    ::= { globalStatistics 35 }

nfsTotalReadMBps OBJECT-TYPE
    SYNTAX         Unsigned32
    MAX-ACCESS     read-only
    STATUS         current
    DESCRIPTION
    "NFS reads, MiBs per second"
    ::= { globalStatistics 36 }

nfsTotalWriteIops OBJECT-TYPE
    SYNTAX         Unsigned32
    MAX-ACCESS     read-only
    STATUS         current
    DESCRIPTION
    "NFS reads, IOs per second"
    ::= { globalStatistics 37 }

nfsTotalReadIops OBJECT-TYPE
    SYNTAX         Unsigned32
    MAX-ACCESS     read-only
    STATUS         current
    DESCRIPTION
    "NFS reads, IOs per second"
    ::= { globalStatistics 38 }

nfsAvgWriteLatency OBJECT-TYPE
    SYNTAX         Unsigned32
    MAX-ACCESS     read-only
    STATUS         current
    DESCRIPTION
    "NFS average write latency in milliseconds"
    ::= { globalStatistics 39 }

nfsAvgReadLatency OBJECT-TYPE
    SYNTAX         Unsigned32
    MAX-ACCESS     read-only
    STATUS         current
    DESCRIPTION
    "NFS average read latency in milliseconds"
    ::= { globalStatistics 40 }

--
-- iscsi Stats
--
iscsiTotalWriteMBps OBJECT-TYPE
    SYNTAX         Unsigned32
    MAX-ACCESS     read-only
    STATUS         current
    DESCRIPTION
    "iSCSI writes, MiBs per second"
    ::= { globalStatistics 41 }

iscsiTotalReadMBps OBJECT-TYPE
    SYNTAX         Unsigned32
    MAX-ACCESS     read-only
    STATUS         current
    DESCRIPTION
    "iSCSI reads, MiBs per second"
    ::= { globalStatistics 42 }

iscsiWriteIops OBJECT-TYPE
    SYNTAX         Unsigned32
    MAX-ACCESS     read-only
    STATUS         current
    DESCRIPTION
    "iSCSI reads, IOs per second"
    ::= { globalStatistics 43 }

iscsiTotalReadIops OBJECT-TYPE
    SYNTAX         Unsigned32
    MAX-ACCESS     read-only
    STATUS         current
    DESCRIPTION
    "iSCSI reads, IOs per second"
    ::= { globalStatistics 44 }

iscsiAvgWriteLatency OBJECT-TYPE
    SYNTAX         Unsigned32
    MAX-ACCESS     read-only
    STATUS         current
    DESCRIPTION
    "iSCSI average write latency in milliseconds"
    ::= { globalStatistics 45 }

iscsiAvgReadLatency OBJECT-TYPE
    SYNTAX         Unsigned32
    MAX-ACCESS     read-only
    STATUS         current
    DESCRIPTION
    "iSCSI average read latency in milliseconds"
    ::= { globalStatistics 46 }

--
-- FC Stats
--
fcTotalWriteMBps OBJECT-TYPE
    SYNTAX         Unsigned32
    MAX-ACCESS     read-only
    STATUS         current
    DESCRIPTION
    "FC writes, MiBs per second"
    ::= { globalStatistics 47 }

fcTotalReadMBps OBJECT-TYPE
    SYNTAX         Unsigned32
    MAX-ACCESS     read-only
    STATUS         current
    DESCRIPTION
    "FC reads, MiBs per second"
    ::= { globalStatistics 48 }

fcTotalWriteIops OBJECT-TYPE
    SYNTAX         Unsigned32
    MAX-ACCESS     read-only
    STATUS         current
    DESCRIPTION
    "FC reads, IOs per second"
    ::= { globalStatistics 49 }

fcTotalReadIops OBJECT-TYPE
    SYNTAX         Unsigned32
    MAX-ACCESS     read-only
    STATUS         current
    DESCRIPTION
    "FC reads, IOs per second"
    ::= { globalStatistics 50 }

fcAvgWriteLatency OBJECT-TYPE
    SYNTAX         Unsigned32
    MAX-ACCESS     read-only
    STATUS         current
    DESCRIPTION
    "FC average write latency in milliseconds"
    ::= { globalStatistics 51 }

fcAvgReadLatency OBJECT-TYPE
    SYNTAX         Unsigned32
    MAX-ACCESS     read-only
    STATUS         current
    DESCRIPTION
    "FC average read latency in milliseconds"
    ::= { globalStatistics 52 }

--
-- VMWare NFS Datastores stats
--
vmwareNFSDatastoresTotalWriteMBps OBJECT-TYPE
    SYNTAX         Unsigned32
    MAX-ACCESS     read-only
    STATUS         current
    DESCRIPTION
    "VMWare NFS Datastores total writes, MiBs per second"
    ::= { globalStatistics 53 }

vmwareNFSDatastoresTotalReadMBps OBJECT-TYPE
    SYNTAX         Unsigned32
    MAX-ACCESS     read-only
    STATUS         current
    DESCRIPTION
    "VMWare NFS Datastores total reads, MiBs per second"
    ::= { globalStatistics 54 }

vmwareNFSDatastoresTotalWriteIops OBJECT-TYPE
    SYNTAX         Unsigned32
    MAX-ACCESS     read-only
    STATUS         current
    DESCRIPTION
    "VMWare NFS Datastores total reads, IOs per second"
    ::= { globalStatistics 55 }

vmwareNFSDatastoresTotalReadIops OBJECT-TYPE
    SYNTAX         Unsigned32
    MAX-ACCESS     read-only
    STATUS         current
    DESCRIPTION
    "VMWare NFS Datastores total reads, IOs per second"
    ::= { globalStatistics 56 }

vmwareNFSDatastoresAvgWriteLatency OBJECT-TYPE
    SYNTAX         Unsigned32
    MAX-ACCESS     read-only
    STATUS         current
    DESCRIPTION
    "VMWare NFS Datastores average write latency in milliseconds"
    ::= { globalStatistics 57 }

vmwareNFSDatastoresAvgReadLatency OBJECT-TYPE
    SYNTAX         Unsigned32
    MAX-ACCESS     read-only
    STATUS         current
    DESCRIPTION
    "VMWare NFS Datastores average read latency in milliseconds"
    ::= { globalStatistics 58 }

        --
-- HyperV SMB VMs stats
--
hypervSMBVMsTotalWriteMBps OBJECT-TYPE
    SYNTAX         Unsigned32
    MAX-ACCESS     read-only
    STATUS         current
    DESCRIPTION
    "HyperV SMB VMs total writes, MiBs per second"
    ::= { globalStatistics 59 }

hypervSMBVMsTotalReadMBps OBJECT-TYPE
    SYNTAX         Unsigned32
    MAX-ACCESS     read-only
    STATUS         current
    DESCRIPTION
    "HyperV SMB VMs total reads, MiBs per second"
    ::= { globalStatistics 60 }

hypervSMBVMsTotalWriteIops OBJECT-TYPE
    SYNTAX         Unsigned32
    MAX-ACCESS     read-only
    STATUS         current
    DESCRIPTION
    "HyperV SMB VMs total reads, IOs per second"
    ::= { globalStatistics 61 }

hypervSMBVMsTotalReadIops OBJECT-TYPE
    SYNTAX         Unsigned32
    MAX-ACCESS     read-only
    STATUS         current
    DESCRIPTION
    "HyperV SMB VMs total reads, IOs per second"
    ::= { globalStatistics 62 }

hypervSMBVMsAvgWriteLatency OBJECT-TYPE
    SYNTAX         Unsigned32
    MAX-ACCESS     read-only
    STATUS         current
    DESCRIPTION
    "HyperV SMB VMs average write latency in milliseconds"
    ::= { globalStatistics 63 }

hypervSMBVMsAvgReadLatency OBJECT-TYPE
    SYNTAX         Unsigned32
    MAX-ACCESS     read-only
    STATUS         current
    DESCRIPTION
    "HyperV SMB VMs average read latency in milliseconds"
    ::= { globalStatistics 64 }

--
-- Network Stats
--
networkTotalReceiveMbps OBJECT-TYPE
    SYNTAX         Unsigned32
    MAX-ACCESS     read-only
    STATUS         current
    DESCRIPTION
    "Network received MB per second"
    ::= { globalStatistics 65 }

networkTotalTransmitMbps OBJECT-TYPE
    SYNTAX         Unsigned32
    MAX-ACCESS     read-only
    STATUS         current
    DESCRIPTION
    "Network transmitted MB per second"
    ::= { globalStatistics 66 }

--
-- End of Global Statistics
--

--
-- Disks
--
diskCount OBJECT-TYPE
    SYNTAX      Unsigned32
    MAX-ACCESS  read-only
    STATUS      current
    DESCRIPTION
    "disks count"
    ::= { disks 1 }

diskTable OBJECT-TYPE
    SYNTAX         SEQUENCE OF DiskEntry
    MAX-ACCESS     not-accessible
    STATUS         current
    DESCRIPTION
    "Disk information table"
    ::= { disks 2 }

diskEntry OBJECT-TYPE
    SYNTAX          DiskEntry
    MAX-ACCESS      not-accessible
    STATUS          current
    DESCRIPTION
    "A row of disk information"
    INDEX { diskChassisIdx,
            diskIndex }
    ::= { diskTable 1 }

DiskEntry ::= SEQUENCE {
    diskChassisIdx          Unsigned32,
    diskIndex               Unsigned32,
    diskAlias               DisplayString,
    diskSize                Counter64,
    diskState               DisplayString,
    diskType                DisplayString,
    diskPoolName            DisplayString
}

diskChassisIdx OBJECT-TYPE
    SYNTAX      Unsigned32
    MAX-ACCESS  not-accessible
    STATUS      current
    DESCRIPTION
    "Disk chassis index"
    ::= { diskEntry 1 }

diskIndex OBJECT-TYPE
    SYNTAX      Unsigned32
    MAX-ACCESS  not-accessible
    STATUS      current
    DESCRIPTION
    "Disk Index."
    ::= { diskEntry 2 }

diskAlias OBJECT-TYPE
    SYNTAX      DisplayString
    MAX-ACCESS  read-only
    STATUS      current
    DESCRIPTION
    "Disk alias"
    ::= { diskEntry 3 }

diskSize OBJECT-TYPE
    SYNTAX      Counter64
    MAX-ACCESS  read-only
    STATUS      current
    DESCRIPTION
    "Disk size in bytes"
    ::= { diskEntry 4 }

diskState OBJECT-TYPE
    SYNTAX      DisplayString
    MAX-ACCESS  read-only
    STATUS      current
    DESCRIPTION
    "Disk state"
    ::= { diskEntry 5 }

diskType OBJECT-TYPE
    SYNTAX      DisplayString
    MAX-ACCESS  read-only
    STATUS      current
    DESCRIPTION
    "Disk type"
    ::= { diskEntry 6 }

diskPoolName OBJECT-TYPE
    SYNTAX      DisplayString
    MAX-ACCESS  read-only
    STATUS      current
    DESCRIPTION
    "Name of the pool disk belongs to"
    ::= { diskEntry 7 }

--
-- End of diskTable
--

--
-- poolTable
--
poolCount OBJECT-TYPE
    SYNTAX         Unsigned32
    MAX-ACCESS     read-only
    STATUS         current
    DESCRIPTION
    "Pool count"
    ::= { pools 1 }

poolTable OBJECT-TYPE
    SYNTAX         SEQUENCE OF PoolEntry
    MAX-ACCESS     not-accessible
    STATUS         current
    DESCRIPTION
    "Pool information table"
    ::= { pools 2 }

poolEntry OBJECT-TYPE
    SYNTAX          PoolEntry
    MAX-ACCESS      not-accessible
    STATUS          current
    DESCRIPTION
    "A row of Pool information"
    INDEX { poolIndex }
    ::= { poolTable 1 }

PoolEntry ::= SEQUENCE {
    poolIndex                           Unsigned32,
    poolName                            DisplayString,
    poolState                           DisplayString,
    poolHealth                          DisplayString,
    poolOwnerController                 DisplayString,
    poolProjectCount                    Unsigned32,
    poolSize                            Counter64,
    poolUsedSize                        Counter64,
    poolFreeSize                        Counter64,
    poolDataSize                        Counter64,
    poolPostDedupDataSize               Counter64,
    poolPostCompressionDataSize         Counter64,
    poolUnusedReservedSize              Counter64,
    poolTotalSaving                     DisplayString,
    poolDataWriteMbps                   Unsigned32,
    poolDataReadMbps                    Unsigned32,
    poolDataWriteIops                   Unsigned32,
    poolDataReadIops                    Unsigned32,
    poolDataWriteLatency                Unsigned32,
    poolDataReadLatency                 Unsigned32,
    poolIFlashWriteMbps                 Unsigned32,
    poolIFlashReadMbps                  Unsigned32,
    poolIFlashWriteIops                 Unsigned32,
    poolIFlashReadIops                  Unsigned32,
    poolIFlashWriteLatency              Unsigned32,
    poolIFlashReadLatency               Unsigned32,
    poolCacheWriteMbps                  Unsigned32,
    poolCacheReadMbps                   Unsigned32,
    poolCacheWriteIops                  Unsigned32,
    poolCacheReadIops                   Unsigned32,
    poolCacheWriteLatency               Unsigned32,
    poolCacheReadLatency                Unsigned32,
    poolMetaWriteMbps                   Unsigned32,
    poolMetaReadMbps                    Unsigned32,
    poolMetaWriteIops                   Unsigned32,
    poolMetaReadIops                    Unsigned32,
    poolMetaWriteLatency                Unsigned32,
    poolMetaReadLatency                 Unsigned32
}

poolIndex OBJECT-TYPE
    SYNTAX      Unsigned32
    MAX-ACCESS  not-accessible
    STATUS      current
    DESCRIPTION
    "Pool Index."
    ::= { poolEntry 1 }

poolName OBJECT-TYPE
    SYNTAX      DisplayString
    MAX-ACCESS  read-only
    STATUS      current
    DESCRIPTION
    "Pool Name"
    ::= { poolEntry 2 }

poolState OBJECT-TYPE
    SYNTAX      DisplayString
    MAX-ACCESS  read-only
    STATUS      current
    DESCRIPTION
    "Pool current state"
    ::= { poolEntry 3 }

poolHealth OBJECT-TYPE
    SYNTAX      DisplayString
    MAX-ACCESS  read-only
    STATUS      current
    DESCRIPTION
    "Pool health status"
    ::= { poolEntry 4 }

poolOwnerController OBJECT-TYPE
    SYNTAX      DisplayString
    MAX-ACCESS  read-only
    STATUS      current
    DESCRIPTION
    "Pool current owner node"
    ::= { poolEntry 5}

poolProjectCount OBJECT-TYPE
    SYNTAX      Unsigned32
    MAX-ACCESS  read-only
    STATUS      current
    DESCRIPTION
    "Count of projects in the Pool"
    ::= { poolEntry 6 }

poolSize OBJECT-TYPE
    SYNTAX      Counter64
    MAX-ACCESS  read-only
    STATUS      current
    DESCRIPTION
    "Size of the Pool in bytes"
    ::= { poolEntry 7 }

poolUsedSize OBJECT-TYPE
    SYNTAX      Counter64
    MAX-ACCESS  read-only
    STATUS      current
    DESCRIPTION
    "Size of used space on Pool in bytes"
    ::= { poolEntry 8 }

poolFreeSize OBJECT-TYPE
    SYNTAX      Counter64
    MAX-ACCESS  read-only
    STATUS      current
    DESCRIPTION
    "Size of free space on Pool in bytes"
    ::= { poolEntry 9 }

poolDataSize OBJECT-TYPE
    SYNTAX      Counter64
    MAX-ACCESS  read-only
    STATUS      current
    DESCRIPTION
    "Size of data on Pool in bytes"
    ::= { poolEntry 10 }

poolPostDedupDataSize OBJECT-TYPE
    SYNTAX      Counter64
    MAX-ACCESS  read-only
    STATUS      current
    DESCRIPTION
    "Size of data after deduplication applied, in bytes"
    ::= { poolEntry 11 }

poolPostCompressionDataSize OBJECT-TYPE
    SYNTAX      Counter64
    MAX-ACCESS  read-only
    STATUS      current
    DESCRIPTION
    "Size of data after compression, in bytes"
    ::= { poolEntry 12 }

poolUnusedReservedSize OBJECT-TYPE
    SYNTAX      Counter64
    MAX-ACCESS  read-only
    STATUS      current
    DESCRIPTION
    "Size of unused/reserved space in bytes"
    ::= { poolEntry 13 }

poolTotalSaving OBJECT-TYPE
    SYNTAX      DisplayString
    MAX-ACCESS  read-only
    STATUS      current
    DESCRIPTION
    "Total savings percentage after deduplication and compression"
    ::= { poolEntry 14 }

poolDataWriteMbps OBJECT-TYPE
    SYNTAX      Unsigned32
    MAX-ACCESS  read-only
    STATUS      current
    DESCRIPTION
    "Pool data writes, MiB per second"
    ::= { poolEntry 15 }

poolDataReadMbps OBJECT-TYPE
    SYNTAX      Unsigned32
    MAX-ACCESS  read-only
    STATUS      current
    DESCRIPTION
    "Pool data reads, MiB per second"
    ::= { poolEntry 16 }

poolDataWriteIops OBJECT-TYPE
    SYNTAX      Unsigned32
    MAX-ACCESS  read-only
    STATUS      current
    DESCRIPTION
    "Pool data writes, IOs per second"
    ::= { poolEntry 17 }

poolDataReadIops OBJECT-TYPE
    SYNTAX      Unsigned32
    MAX-ACCESS  read-only
    STATUS      current
    DESCRIPTION
    "Pool data reads, IOs per second"
    ::= { poolEntry 18 }

poolDataWriteLatency OBJECT-TYPE
    SYNTAX      Unsigned32
    MAX-ACCESS  read-only
    STATUS      current
    DESCRIPTION
    "Average pool data write latency in milliseconds"
    ::= { poolEntry 19 }

poolDataReadLatency OBJECT-TYPE
    SYNTAX      Unsigned32
    MAX-ACCESS  read-only
    STATUS      current
    DESCRIPTION
    "Average pool data read latency in milliseconds"
    ::= { poolEntry 20 }

poolIFlashWriteMbps OBJECT-TYPE
    SYNTAX      Unsigned32
    MAX-ACCESS  read-only
    STATUS      current
    DESCRIPTION
    "Pool iFlash writes, MiB per second"
    ::= { poolEntry 21 }

poolIFlashReadMbps OBJECT-TYPE
    SYNTAX      Unsigned32
    MAX-ACCESS  read-only
    STATUS      current
    DESCRIPTION
    "Pool iFlash reads, MiB per second"
    ::= { poolEntry 22 }

poolIFlashWriteIops OBJECT-TYPE
    SYNTAX      Unsigned32
    MAX-ACCESS  read-only
    STATUS      current
    DESCRIPTION
    "Pool iFlash writes, IOs per second"
    ::= { poolEntry 23 }

poolIFlashReadIops OBJECT-TYPE
    SYNTAX      Unsigned32
    MAX-ACCESS  read-only
    STATUS      current
    DESCRIPTION
    "Pool iFlash reads, IOs per second"
    ::= { poolEntry 24 }

poolIFlashWriteLatency OBJECT-TYPE
    SYNTAX      Unsigned32
    MAX-ACCESS  read-only
    STATUS      current
    DESCRIPTION
    "Average pool iFlash write latency in milliseconds"
    ::= { poolEntry 25 }

poolIFlashReadLatency OBJECT-TYPE
    SYNTAX      Unsigned32
    MAX-ACCESS  read-only
    STATUS      current
    DESCRIPTION
    "Average pool iFlash read latency in milliseconds"
    ::= { poolEntry 26 }

poolCacheWriteMbps OBJECT-TYPE
    SYNTAX      Unsigned32
    MAX-ACCESS  read-only
    STATUS      current
    DESCRIPTION
    "Pool cache writes, MiB per second"
    ::= { poolEntry 27 }

poolCacheReadMbps OBJECT-TYPE
    SYNTAX      Unsigned32
    MAX-ACCESS  read-only
    STATUS      current
    DESCRIPTION
    "Pool cache reads, MiB per second"
    ::= { poolEntry 28 }

poolCacheWriteIops OBJECT-TYPE
    SYNTAX      Unsigned32
    MAX-ACCESS  read-only
    STATUS      current
    DESCRIPTION
    "Pool cache writes, IOs per second"
    ::= { poolEntry 29 }

poolCacheReadIops OBJECT-TYPE
    SYNTAX      Unsigned32
    MAX-ACCESS  read-only
    STATUS      current
    DESCRIPTION
    "Pool cache reads, IOs per second"
    ::= { poolEntry 30 }

poolCacheWriteLatency OBJECT-TYPE
    SYNTAX      Unsigned32
    MAX-ACCESS  read-only
    STATUS      current
    DESCRIPTION
    "Average pool cache write latency"
    ::= { poolEntry 31 }

poolCacheReadLatency OBJECT-TYPE
    SYNTAX      Unsigned32
    MAX-ACCESS  read-only
    STATUS      current
    DESCRIPTION
    "Average pool cache read latency"
    ::= { poolEntry 32 }

poolMetaWriteMbps OBJECT-TYPE
    SYNTAX      Unsigned32
    MAX-ACCESS  read-only
    STATUS      current
    DESCRIPTION
    "Pool meta-data writes, MiB per second"
    ::= { poolEntry 33 }

poolMetaReadMbps OBJECT-TYPE
    SYNTAX      Unsigned32
    MAX-ACCESS  read-only
    STATUS      current
    DESCRIPTION
    "Pool meta-data reads, MiB per second"
    ::= { poolEntry 34 }

poolMetaWriteIops OBJECT-TYPE
    SYNTAX      Unsigned32
    MAX-ACCESS  read-only
    STATUS      current
    DESCRIPTION
    "Pool meta-data writes, IOs per second"
    ::= { poolEntry 35 }

poolMetaReadIops OBJECT-TYPE
    SYNTAX      Unsigned32
    MAX-ACCESS  read-only
    STATUS      current
    DESCRIPTION
    "Pool meta-data reads, IOs per second"
    ::= { poolEntry 36 }

poolMetaWriteLatency OBJECT-TYPE
    SYNTAX      Unsigned32
    MAX-ACCESS  read-only
    STATUS      current
    DESCRIPTION
    "Average pool meta-data write latency"
    ::= { poolEntry 37 }

poolMetaReadLatency OBJECT-TYPE
    SYNTAX      Unsigned32
    MAX-ACCESS  read-only
    STATUS      current
    DESCRIPTION
    "Average pool meta-data read latency"
    ::= { poolEntry 38 }

--
-- End of poolTable
--

--
-- projectTable
--
projectTable OBJECT-TYPE
    SYNTAX         SEQUENCE OF ProjectEntry
    MAX-ACCESS     not-accessible
    STATUS         current
    DESCRIPTION
    "Project information table"
    ::= { poolProjects 1 }

projectEntry OBJECT-TYPE
    SYNTAX          ProjectEntry
    MAX-ACCESS      not-accessible
    STATUS          current
    DESCRIPTION
    "A row of Project information"
    INDEX { poolIndex,
            projectIndex }
    ::= { projectTable 1 }

ProjectEntry ::= SEQUENCE {
    projectIndex                            Unsigned32,
    projectName                             DisplayString,
    projectPoolName                         DisplayString,
    projectDedupEnabled                     DisplayString,
    projectCompressionEnabled               DisplayString,
    projectQuotaSize                        Counter64,
    projectDataSize                         Counter64,
    projectFreeSize                         Counter64,
    projectSnapshotSize                     Counter64,
    projectPostCompressionDataSize          Counter64,
    projectUnusedReservedSize               Counter64,
    projectTotalSaving                      DisplayString,
    projectLunCount                         Unsigned32,
    projectShareCount                       Unsigned32
}

projectIndex OBJECT-TYPE
    SYNTAX      Unsigned32
    MAX-ACCESS  not-accessible
    STATUS      current
    DESCRIPTION
    "Project Index."
    ::= { projectEntry 1 }

projectName OBJECT-TYPE
    SYNTAX      DisplayString
    MAX-ACCESS  read-only
    STATUS      current
    DESCRIPTION
    "Project Name"
    ::= { projectEntry 2 }

projectPoolName OBJECT-TYPE
    SYNTAX      DisplayString
    MAX-ACCESS  read-only
    STATUS      current
    DESCRIPTION
    "Project's pool Name"
    ::= { projectEntry 3 }

projectDedupEnabled OBJECT-TYPE
    SYNTAX      DisplayString
    MAX-ACCESS  read-only
    STATUS      current
    DESCRIPTION
    "Flag indicating if Dedup is enabled for the Project or not"
    ::= { projectEntry 4 }

projectCompressionEnabled OBJECT-TYPE
    SYNTAX      DisplayString
    MAX-ACCESS  read-only
    STATUS      current
    DESCRIPTION
    "Flag indicating if Compression is enabled for the Project or not"
    ::= { projectEntry 5 }

projectQuotaSize OBJECT-TYPE
    SYNTAX      Counter64
    MAX-ACCESS  read-only
    STATUS      current
    DESCRIPTION
    "Project quota size in bytes"
    ::= { projectEntry 6 }

projectDataSize OBJECT-TYPE
    SYNTAX      Counter64
    MAX-ACCESS  read-only
    STATUS      current
    DESCRIPTION
    "Size of data in Project in bytes"
    ::= { projectEntry 7 }

projectFreeSize OBJECT-TYPE
    SYNTAX      Counter64
    MAX-ACCESS  read-only
    STATUS      current
    DESCRIPTION
    "Size of free space in Project in bytes"
    ::= { projectEntry 8 }

projectSnapshotSize OBJECT-TYPE
    SYNTAX      Counter64
    MAX-ACCESS  read-only
    STATUS      current
    DESCRIPTION
    "Size of snapshots in bytes"
    ::= { projectEntry 9 }

projectPostCompressionDataSize OBJECT-TYPE
    SYNTAX      Counter64
    MAX-ACCESS  read-only
    STATUS      current
    DESCRIPTION
    "Size of data after compression, in bytes"
    ::= { projectEntry 10 }

projectUnusedReservedSize OBJECT-TYPE
    SYNTAX      Counter64
    MAX-ACCESS  read-only
    STATUS      current
    DESCRIPTION
    "Size of unused/reserved space in bytes"
    ::= { projectEntry 11 }

projectTotalSaving OBJECT-TYPE
    SYNTAX      DisplayString
    MAX-ACCESS  read-only
    STATUS      current
    DESCRIPTION
    "Total savings percentage after deduplication and compression"
    ::= { projectEntry 12 }

projectLunCount OBJECT-TYPE
    SYNTAX      Unsigned32
    MAX-ACCESS  read-only
    STATUS      current
    DESCRIPTION
    "Project LUN Count"
    ::= { projectEntry 13 }

projectShareCount OBJECT-TYPE
    SYNTAX      Unsigned32
    MAX-ACCESS  read-only
    STATUS      current
    DESCRIPTION
    "Project Share count"
    ::= { projectEntry 14 }

--
-- End of projectTable
--

--
-- lunTable
--
lunTable OBJECT-TYPE
    SYNTAX         SEQUENCE OF LUNEntry
    MAX-ACCESS     not-accessible
    STATUS         current
    DESCRIPTION
    "LUN information table"
    ::= { projectLUNs 3 }

lunEntry OBJECT-TYPE
    SYNTAX          LUNEntry
    MAX-ACCESS      not-accessible
    STATUS          current
    DESCRIPTION
    "A row of LUN information"
    INDEX { poolIndex,
            projectIndex,
            lunIndex }
    ::= { lunTable 1 }

LUNEntry ::= SEQUENCE {
    lunIndex                    Unsigned32,
    lunName                     DisplayString,
    lunProjectName              DisplayString,
    lunPoolName                 DisplayString,
    lunGUID                     DisplayString,
    lunBlockSize                DisplayString,
    lunDedupEnabled             DisplayString,
    lunCompressionEnabled       DisplayString,
    lunSize                     Counter64,
    lunDataSize                 Counter64,
    lunSnapshotSize             Counter64,
    lunFreeSize                 Counter64,
    lunReservedSize             Counter64,
    lunCompressedRatio          Unsigned32,
    lunProtocol                 DisplayString,
    lunTargetGroup              DisplayString,
    lunInitiatorGroup           DisplayString,
    lunWriteMBps                Unsigned32,
    lunReadMBps                 Unsigned32,
    lunWriteIops                Unsigned32,
    lunReadIops                 Unsigned32,
    lunWriteLatency             Unsigned32,
    lunReadLatency              Unsigned32
}

lunIndex OBJECT-TYPE
    SYNTAX      Unsigned32
    MAX-ACCESS  not-accessible
    STATUS      current
    DESCRIPTION
    "LUN Index."
    ::= { lunEntry 1 }

lunName OBJECT-TYPE
    SYNTAX      DisplayString
    MAX-ACCESS  read-only
    STATUS      current
    DESCRIPTION
    "LUN Name"
    ::= { lunEntry 2 }

lunProjectName OBJECT-TYPE
    SYNTAX      DisplayString
    MAX-ACCESS  read-only
    STATUS      current
    DESCRIPTION
    "LUN Project Name"
    ::= { lunEntry 3 }

lunPoolName OBJECT-TYPE
    SYNTAX      DisplayString
    MAX-ACCESS  read-only
    STATUS      current
    DESCRIPTION
    "LUN Pool Name"
    ::= { lunEntry 4 }

lunGUID OBJECT-TYPE
    SYNTAX      DisplayString
    MAX-ACCESS  read-only
    STATUS      current
    DESCRIPTION
    "LUN GUID"
    ::= { lunEntry 5 }

lunBlockSize OBJECT-TYPE
    SYNTAX      DisplayString
    MAX-ACCESS  read-only
    STATUS      current
    DESCRIPTION
    "LUN block size string"
    ::= { lunEntry 6 }

lunDedupEnabled OBJECT-TYPE
    SYNTAX      DisplayString
    MAX-ACCESS  read-only
    STATUS      current
    DESCRIPTION
    "Flag indicating if Dedup is enabled for the LUN or not"
    ::= { lunEntry 7 }

lunCompressionEnabled OBJECT-TYPE
    SYNTAX      DisplayString
    MAX-ACCESS  read-only
    STATUS      current
    DESCRIPTION
    "Flag indicating if Compression is enabled for the LUN or not"
    ::= { lunEntry 8 }

lunSize OBJECT-TYPE
    SYNTAX      Counter64
    MAX-ACCESS  read-only
    STATUS      current
    DESCRIPTION
    "LUN size in bytes"
    ::= { lunEntry 9 }

lunDataSize OBJECT-TYPE
    SYNTAX      Counter64
    MAX-ACCESS  read-only
    STATUS      current
    DESCRIPTION
    "Size of Data on LUN in bytes"
    ::= { lunEntry 10 }

lunSnapshotSize OBJECT-TYPE
    SYNTAX      Counter64
    MAX-ACCESS  read-only
    STATUS      current
    DESCRIPTION
    "Size of Snapshots of LUN in bytes"
    ::= { lunEntry 11 }

lunFreeSize OBJECT-TYPE
    SYNTAX      Counter64
    MAX-ACCESS  read-only
    STATUS      current
    DESCRIPTION
    "Free space available on LUN in bytes"
    ::= { lunEntry 12 }

lunReservedSize OBJECT-TYPE
    SYNTAX      Counter64
    MAX-ACCESS  read-only
    STATUS      current
    DESCRIPTION
    "Size of the space reserved on LUN in bytes"
    ::= { lunEntry 13 }

lunCompressedRatio OBJECT-TYPE
    SYNTAX      Unsigned32
    MAX-ACCESS  read-only
    STATUS      current
    DESCRIPTION
    "Percentage of data compressed on LUN"
    ::= { lunEntry 14 }

lunProtocol OBJECT-TYPE
    SYNTAX      DisplayString
    MAX-ACCESS  read-only
    STATUS      current
    DESCRIPTION
    "LUN access protocol"
    ::= { lunEntry 15 }

lunTargetGroup OBJECT-TYPE
    SYNTAX      DisplayString
    MAX-ACCESS  read-only
    STATUS      current
    DESCRIPTION
    "Name of the LUN Target group"
    ::= { lunEntry 16 }

lunInitiatorGroup OBJECT-TYPE
    SYNTAX      DisplayString
    MAX-ACCESS  read-only
    STATUS      current
    DESCRIPTION
    "Name of the LUN Initiator group"
    ::= { lunEntry 17 }

lunWriteMBps OBJECT-TYPE
    SYNTAX      Unsigned32
    MAX-ACCESS  read-only
    STATUS      current
    DESCRIPTION
    "Lun writes, MiB per second"
    ::= { lunEntry 18 }

lunReadMBps OBJECT-TYPE
    SYNTAX      Unsigned32
    MAX-ACCESS  read-only
    STATUS      current
    DESCRIPTION
    "Lun reads, MiB per second"
    ::= { lunEntry 19 }

lunWriteIops OBJECT-TYPE
    SYNTAX      Unsigned32
    MAX-ACCESS  read-only
    STATUS      current
    DESCRIPTION
    "Lun writes, IOs per second"
    ::= { lunEntry 20 }

lunReadIops OBJECT-TYPE
    SYNTAX      Unsigned32
    MAX-ACCESS  read-only
    STATUS      current
    DESCRIPTION
    "Lun reads, IOs per second"
    ::= { lunEntry 21 }

lunWriteLatency OBJECT-TYPE
    SYNTAX      Unsigned32
    MAX-ACCESS  read-only
    STATUS      current
    DESCRIPTION
    "Average lun write latency"
    ::= { lunEntry 22 }

lunReadLatency OBJECT-TYPE
    SYNTAX      Unsigned32
    MAX-ACCESS  read-only
    STATUS      current
    DESCRIPTION
    "Average lun read latency"
    ::= { lunEntry 23 }
--
-- End of lunTable
--

--
-- shareTable
--
shareTable OBJECT-TYPE
    SYNTAX         SEQUENCE OF ShareEntry
    MAX-ACCESS     not-accessible
    STATUS         current
    DESCRIPTION
    "Project Shares information table"
    ::= { projectShares 1 }

shareEntry OBJECT-TYPE
    SYNTAX          ShareEntry
    MAX-ACCESS      not-accessible
    STATUS          current
    DESCRIPTION
    "A row of Shares information"
    INDEX { poolIndex,
            projectIndex,
            shareIndex }
    ::= { shareTable 1 }

ShareEntry ::= SEQUENCE {
    shareIndex                  Unsigned32,
    shareName                   DisplayString,
    shareMountPoint             DisplayString,
    shareProjectName            DisplayString,
    sharePoolName               DisplayString,
    shareQuota                  Counter64,
    shareNFSEnabled             DisplayString,
    shareCIFSEnabled            DisplayString,
    shareDedupEnabled           DisplayString,
    shareCompressionEnabled     DisplayString,
    shareDataSize               Counter64,
    shareSnapshotSize           Counter64,
    shareReservedSize           Counter64,
    shareCompressedRatio        Unsigned32,
    shareCIFSWriteMBps          Unsigned32,
    shareCIFSReadMBps           Unsigned32,
    shareCIFSWriteIops          Unsigned32,
    shareCIFSReadIops           Unsigned32,
    shareCIFSWriteLatency       Unsigned32,
    shareCIFSReadLatency        Unsigned32,
    shareNFSWriteMBps           Unsigned32,
    shareNFSReadMBps            Unsigned32,
    shareNFSWriteIops           Unsigned32,
    shareNFSReadIops            Unsigned32,
    shareNFSWriteLatency        Unsigned32,
    shareNFSReadLatency         Unsigned32
}

shareIndex OBJECT-TYPE
    SYNTAX      Unsigned32
    MAX-ACCESS  not-accessible
    STATUS      current
    DESCRIPTION
    "Share Index."
    ::= { shareEntry 1 }

shareName OBJECT-TYPE
    SYNTAX      DisplayString
    MAX-ACCESS  read-only
    STATUS      current
    DESCRIPTION
    "Share name"
    ::= { shareEntry 2 }

shareMountPoint OBJECT-TYPE
    SYNTAX      DisplayString
    MAX-ACCESS  read-only
    STATUS      current
    DESCRIPTION
    "Share mount point"
    ::= { shareEntry 3 }

shareProjectName OBJECT-TYPE
    SYNTAX      DisplayString
    MAX-ACCESS  read-only
    STATUS      current
    DESCRIPTION
    "Share Project name"
    ::= { shareEntry 4 }

sharePoolName OBJECT-TYPE
    SYNTAX      DisplayString
    MAX-ACCESS  read-only
    STATUS      current
    DESCRIPTION
    "Share Pool name"
    ::= { shareEntry 5 }

shareQuota OBJECT-TYPE
    SYNTAX      Counter64
    MAX-ACCESS  read-only
    STATUS      current
    DESCRIPTION
    "Share quota size in bytes"
    ::= { shareEntry 6 }

shareNFSEnabled OBJECT-TYPE
    SYNTAX      DisplayString
    MAX-ACCESS  read-only
    STATUS      current
    DESCRIPTION
    "Flag indicating if NFS access is enabled for this share or not"
    ::= { shareEntry 7 }

shareCIFSEnabled OBJECT-TYPE
    SYNTAX      DisplayString
    MAX-ACCESS  read-only
    STATUS      current
    DESCRIPTION
    "Flag indicating if CIFS access is enabled for this share or not"
    ::= { shareEntry 8 }

shareDedupEnabled OBJECT-TYPE
    SYNTAX      DisplayString
    MAX-ACCESS  read-only
    STATUS      current
    DESCRIPTION
    "Flag indicating if Dedup is enabled for the LUN or not"
    ::= { shareEntry 9 }

shareCompressionEnabled OBJECT-TYPE
    SYNTAX      DisplayString
    MAX-ACCESS  read-only
    STATUS      current
    DESCRIPTION
    "Flag indicating if Compression is enabled for the LUN or not"
    ::= { shareEntry 10 }

shareDataSize OBJECT-TYPE
    SYNTAX      Counter64
    MAX-ACCESS  read-only
    STATUS      current
    DESCRIPTION
    "Size of Data on the share in bytes"
    ::= { shareEntry 11 }

shareSnapshotSize OBJECT-TYPE
    SYNTAX      Counter64
    MAX-ACCESS  read-only
    STATUS      current
    DESCRIPTION
    "Size of Snapshots of the share in bytes"
    ::= { shareEntry 12 }

shareReservedSize OBJECT-TYPE
    SYNTAX      Counter64
    MAX-ACCESS  read-only
    STATUS      current
    DESCRIPTION
    "Reserved space on the share in bytes"
    ::= { shareEntry 13 }

shareCompressedRatio OBJECT-TYPE
    SYNTAX      Unsigned32
    MAX-ACCESS  read-only
    STATUS      current
    DESCRIPTION
    "Percentage of data compressed on the Share"
    ::= { shareEntry 14 }

shareCIFSWriteMBps OBJECT-TYPE
    SYNTAX      Unsigned32
    MAX-ACCESS  read-only
    STATUS      current
    DESCRIPTION
    "Share CIFS writes, MiB per second"
    ::= { shareEntry 15 }

shareCIFSReadMBps OBJECT-TYPE
    SYNTAX      Unsigned32
    MAX-ACCESS  read-only
    STATUS      current
    DESCRIPTION
    "Share CIFS reads, MiB per second"
    ::= { shareEntry 16 }

shareCIFSWriteIops OBJECT-TYPE
    SYNTAX      Unsigned32
    MAX-ACCESS  read-only
    STATUS      current
    DESCRIPTION
    "Share CIFS write IOs per second"
    ::= { shareEntry 17 }

shareCIFSReadIops OBJECT-TYPE
    SYNTAX      Unsigned32
    MAX-ACCESS  read-only
    STATUS      current
    DESCRIPTION
    "Share CIFS read IOs per second"
    ::= { shareEntry 18 }

shareCIFSWriteLatency OBJECT-TYPE
    SYNTAX      Unsigned32
    MAX-ACCESS  read-only
    STATUS      current
    DESCRIPTION
    "Share CIFS write latency"
    ::= { shareEntry 19 }

shareCIFSReadLatency OBJECT-TYPE
    SYNTAX      Unsigned32
    MAX-ACCESS  read-only
    STATUS      current
    DESCRIPTION
    "Share CIFS read latency"
    ::= { shareEntry 20 }

shareNFSWriteMBps OBJECT-TYPE
    SYNTAX      Unsigned32
    MAX-ACCESS  read-only
    STATUS      current
    DESCRIPTION
    "Share NFS writes, MiB per second"
    ::= { shareEntry 21 }

shareNFSReadMBps OBJECT-TYPE
    SYNTAX      Unsigned32
    MAX-ACCESS  read-only
    STATUS      current
    DESCRIPTION
    "Share NFS reads, MiB per second"
    ::= { shareEntry 22 }

shareNFSWriteIops OBJECT-TYPE
    SYNTAX      Unsigned32
    MAX-ACCESS  read-only
    STATUS      current
    DESCRIPTION
    "Share NFS write IOs per second"
    ::= { shareEntry 23 }

shareNFSReadIops OBJECT-TYPE
    SYNTAX      Unsigned32
    MAX-ACCESS  read-only
    STATUS      current
    DESCRIPTION
    "Share NFS read IOs per second"
    ::= { shareEntry 24 }

shareNFSWriteLatency OBJECT-TYPE
    SYNTAX      Unsigned32
    MAX-ACCESS  read-only
    STATUS      current
    DESCRIPTION
    "Share NFS write latency"
    ::= { shareEntry 25 }

shareNFSReadLatency OBJECT-TYPE
    SYNTAX      Unsigned32
    MAX-ACCESS  read-only
    STATUS      current
    DESCRIPTION
    "Share NFS read latency"
    ::= { shareEntry 26 }

--
-- End of shareTable
--

--
-- iscsiTargetsTable
--
iscsiTargetsTable OBJECT-TYPE
    SYNTAX         SEQUENCE OF ISCSITargetEntry
    MAX-ACCESS     not-accessible
    STATUS         current
    DESCRIPTION
    "iSCSI Targets information table"
    ::= { iscsiTargets 1 }

iscsiTargetEntry OBJECT-TYPE
    SYNTAX          ISCSITargetEntry
    MAX-ACCESS      not-accessible
    STATUS          current
    DESCRIPTION
    "A row of iSCSI Targets information"
    INDEX { iscsiTargetIndex }
    ::= { iscsiTargetsTable 1 }

ISCSITargetEntry ::= SEQUENCE {
    iscsiTargetIndex            Unsigned32,
    iscsiTargetName             DisplayString,
    iscsiTargetAlias            DisplayString,
    iscsiTargetGroup            DisplayString,
    iscsiTargetAuth             DisplayString,
    iscsiTargetWriteMBps        Unsigned32,
    iscsiTargetReadMBps         Unsigned32,
    iscsiTargetWriteIops        Unsigned32,
    iscsiTargetReadIops         Unsigned32,
    iscsiTargetWriteLatency     Unsigned32,
    iscsiTargetReadLatency      Unsigned32
}

iscsiTargetIndex OBJECT-TYPE
    SYNTAX      Unsigned32
    MAX-ACCESS  not-accessible
    STATUS      current
    DESCRIPTION
    "iSCSI Target Index."
    ::= { iscsiTargetEntry 1 }

iscsiTargetName OBJECT-TYPE
    SYNTAX      DisplayString
    MAX-ACCESS  read-only
    STATUS      current
    DESCRIPTION
    "iSCSI Target name"
    ::= { iscsiTargetEntry 2 }

iscsiTargetAlias OBJECT-TYPE
    SYNTAX      DisplayString
    MAX-ACCESS  read-only
    STATUS      current
    DESCRIPTION
    "iSCSI Target alias"
    ::= { iscsiTargetEntry 3 }

iscsiTargetGroup OBJECT-TYPE
    SYNTAX      DisplayString
    MAX-ACCESS  read-only
    STATUS      current
    DESCRIPTION
    "iSCSI Target alias"
    ::= { iscsiTargetEntry 4 }

iscsiTargetAuth OBJECT-TYPE
    SYNTAX      DisplayString
    MAX-ACCESS  read-only
    STATUS      current
    DESCRIPTION
    "iSCSI Target authentication"
    ::= { iscsiTargetEntry 5 }

iscsiTargetWriteMBps OBJECT-TYPE
    SYNTAX         Unsigned32
    MAX-ACCESS     read-only
    STATUS         current
    DESCRIPTION
    "iSCSI Target writes, MiBs per second"
    ::= { iscsiTargetEntry 6 }

iscsiTargetReadMBps OBJECT-TYPE
    SYNTAX         Unsigned32
    MAX-ACCESS     read-only
    STATUS         current
    DESCRIPTION
    "iSCSI Target reads, MiBs per second"
    ::= { iscsiTargetEntry 7 }

iscsiTargetWriteIops OBJECT-TYPE
    SYNTAX         Unsigned32
    MAX-ACCESS     read-only
    STATUS         current
    DESCRIPTION
    "iSCSI Target writes, IOs per second"
    ::= { iscsiTargetEntry 8 }

iscsiTargetReadIops OBJECT-TYPE
    SYNTAX         Unsigned32
    MAX-ACCESS     read-only
    STATUS         current
    DESCRIPTION
    "iSCSI Target reads, IOs per second"
    ::= { iscsiTargetEntry 9 }

iscsiTargetWriteLatency OBJECT-TYPE
    SYNTAX         Unsigned32
    MAX-ACCESS     read-only
    STATUS         current
    DESCRIPTION
    "iSCSI Target average write latency"
    ::= { iscsiTargetEntry 10 }

iscsiTargetReadLatency OBJECT-TYPE
    SYNTAX         Unsigned32
    MAX-ACCESS     read-only
    STATUS         current
    DESCRIPTION
    "iSCSI Target average read latency"
    ::= { iscsiTargetEntry 11 }

--
-- End of iscsiTargetTable
--

--
-- iscsiInitiatorsTable
--
iscsiInitiatorsTable OBJECT-TYPE
    SYNTAX         SEQUENCE OF ISCSIInitiatorEntry
    MAX-ACCESS     not-accessible
    STATUS         current
    DESCRIPTION
    "iSCSI Initiators information table"
    ::= { iscsiInitiators 1 }

iscsiInitiatorEntry OBJECT-TYPE
    SYNTAX          ISCSIInitiatorEntry
    MAX-ACCESS      not-accessible
    STATUS          current
    DESCRIPTION
    "A row of iSCSI Initiators information"
    INDEX { iscsiInitiatorIndex }
    ::= { iscsiInitiatorsTable 1 }

ISCSIInitiatorEntry ::= SEQUENCE {
    iscsiInitiatorIndex            Unsigned32,
    iscsiInitiatorName             DisplayString,
    iscsiInitiatorChapUser         DisplayString,
    iscsiInitiatorGroup            DisplayString
}

iscsiInitiatorIndex OBJECT-TYPE
    SYNTAX      Unsigned32
    MAX-ACCESS  not-accessible
    STATUS      current
    DESCRIPTION
    "iSCSI Initiator Index."
    ::= { iscsiInitiatorEntry 1 }

iscsiInitiatorName OBJECT-TYPE
    SYNTAX      DisplayString
    MAX-ACCESS  read-only
    STATUS      current
    DESCRIPTION
    "iSCSI Initiator name"
    ::= { iscsiInitiatorEntry 2 }

iscsiInitiatorChapUser OBJECT-TYPE
    SYNTAX      DisplayString
    MAX-ACCESS  read-only
    STATUS      current
    DESCRIPTION
    "iSCSI Initiator CHAP user"
    ::= { iscsiInitiatorEntry 3 }

iscsiInitiatorGroup OBJECT-TYPE
    SYNTAX      DisplayString
    MAX-ACCESS  read-only
    STATUS      current
    DESCRIPTION
    "iSCSI Initiator group"
    ::= { iscsiInitiatorEntry 4 }

--
-- End of iscsiInitiatorTable
--

--
-- fcTargetsTable
--
fcTargetsTable OBJECT-TYPE
    SYNTAX         SEQUENCE OF FCTargetEntry
    MAX-ACCESS     not-accessible
    STATUS         current
    DESCRIPTION
    "FC Targets information table"
    ::= { fcTargets 1 }

fcTargetEntry OBJECT-TYPE
    SYNTAX          FCTargetEntry
    MAX-ACCESS      not-accessible
    STATUS          current
    DESCRIPTION
    "A row of FC Targets information"
    INDEX { fcTargetIndex }
    ::= { fcTargetsTable 1 }

FCTargetEntry ::= SEQUENCE {
    fcTargetIndex           Unsigned32,
    fcTargetName            DisplayString,
    fcTargetStatus          DisplayString,
    fcTargetGroup           DisplayString,
    fcTargetCurrentSpeed    DisplayString,
    fcTargetWriteMBps       Unsigned32,
    fcTargetReadMBps        Unsigned32,
    fcTargetWriteIops       Unsigned32,
    fcTargetReadIops        Unsigned32,
    fcTargetWriteLatency    Unsigned32,
    fcTargetReadLatency     Unsigned32
}

fcTargetIndex OBJECT-TYPE
    SYNTAX      Unsigned32
    MAX-ACCESS  not-accessible
    STATUS      current
    DESCRIPTION
    "FC Target Index."
    ::= { fcTargetEntry 1 }

fcTargetName OBJECT-TYPE
    SYNTAX      DisplayString
    MAX-ACCESS  read-only
    STATUS      current
    DESCRIPTION
    "FC Target name"
    ::= { fcTargetEntry 2 }

fcTargetStatus OBJECT-TYPE
    SYNTAX      DisplayString
    MAX-ACCESS  read-only
    STATUS      current
    DESCRIPTION
    "FC Target status"
    ::= { fcTargetEntry 3 }

fcTargetGroup OBJECT-TYPE
    SYNTAX      DisplayString
    MAX-ACCESS  read-only
    STATUS      current
    DESCRIPTION
    "FC Target group"
    ::= { fcTargetEntry 4 }

fcTargetCurrentSpeed OBJECT-TYPE
    SYNTAX         DisplayString
    MAX-ACCESS     read-only
    STATUS         current
    DESCRIPTION
    "FC Target current speed in GB"
    ::= { fcTargetEntry 5 }

fcTargetWriteMBps OBJECT-TYPE
    SYNTAX         Unsigned32
    MAX-ACCESS     read-only
    STATUS         current
    DESCRIPTION
    "FC Target writes, MiBs per second"
    ::= { fcTargetEntry 6 }

fcTargetReadMBps OBJECT-TYPE
    SYNTAX         Unsigned32
    MAX-ACCESS     read-only
    STATUS         current
    DESCRIPTION
    "FC Target reads, MiBs per second"
    ::= { fcTargetEntry 7 }

fcTargetWriteIops OBJECT-TYPE
    SYNTAX         Unsigned32
    MAX-ACCESS     read-only
    STATUS         current
    DESCRIPTION
    "FC Target writes, IOs per second"
    ::= { fcTargetEntry 8 }

fcTargetReadIops OBJECT-TYPE
    SYNTAX         Unsigned32
    MAX-ACCESS     read-only
    STATUS         current
    DESCRIPTION
    "FC Target reads, IOs per second"
    ::= { fcTargetEntry 9 }

fcTargetWriteLatency OBJECT-TYPE
    SYNTAX         Unsigned32
    MAX-ACCESS     read-only
    STATUS         current
    DESCRIPTION
    "FC Target average write latency"
    ::= { fcTargetEntry 10 }

fcTargetReadLatency OBJECT-TYPE
    SYNTAX         Unsigned32
    MAX-ACCESS     read-only
    STATUS         current
    DESCRIPTION
    "FC Target average read latency"
    ::= { fcTargetEntry 11 }

--
-- End of fcTargetTable
--

--
-- fcInitiatorsTable
--
fcInitiatorsTable OBJECT-TYPE
    SYNTAX         SEQUENCE OF FCInitiatorEntry
    MAX-ACCESS     not-accessible
    STATUS         current
    DESCRIPTION
    "FC Initiators information table"
    ::= { fcInitiators 1 }

fcInitiatorEntry OBJECT-TYPE
    SYNTAX          FCInitiatorEntry
    MAX-ACCESS      not-accessible
    STATUS          current
    DESCRIPTION
    "A row of FC Initiators information"
    INDEX { fcInitiatorIndex }
    ::= { fcInitiatorsTable 1 }

FCInitiatorEntry ::= SEQUENCE {
    fcInitiatorIndex            Unsigned32,
    fcInitiatorName             DisplayString,
    fcInitiatorGroup            DisplayString
}

fcInitiatorIndex OBJECT-TYPE
    SYNTAX      Unsigned32
    MAX-ACCESS  not-accessible
    STATUS      current
    DESCRIPTION
    "FC Initiator Index."
    ::= { fcInitiatorEntry 1 }

fcInitiatorName OBJECT-TYPE
    SYNTAX      DisplayString
    MAX-ACCESS  read-only
    STATUS      current
    DESCRIPTION
    "FC Initiator name"
    ::= { fcInitiatorEntry 2 }

fcInitiatorGroup OBJECT-TYPE
    SYNTAX      DisplayString
    MAX-ACCESS  read-only
    STATUS      current
    DESCRIPTION
    "FC Initiator group"
    ::= { fcInitiatorEntry 3 }

--
-- End of fcInitiatorTable
--

--
-- vmware NFS Datastores Table
--
vmwareNFSDatastoresTable OBJECT-TYPE
    SYNTAX         SEQUENCE OF VMWareNFSDatastoreEntry
    MAX-ACCESS     not-accessible
    STATUS         current
    DESCRIPTION
    "VMWare NFS Datastores information table"
    ::= { vmwareNFSDatastores 1 }

vmwareNFSDatastoreEntry OBJECT-TYPE
    SYNTAX          VMWareNFSDatastoreEntry
    MAX-ACCESS      not-accessible
    STATUS          current
    DESCRIPTION
    "A row of VMWare NFS Datastores information"
    INDEX { vmwareNFSDatastoreIndex }
    ::= { vmwareNFSDatastoresTable 1 }

VMWareNFSDatastoreEntry ::= SEQUENCE {
    vmwareNFSDatastoreIndex             Unsigned32,
    vmwareNFSDatastoreVMName            DisplayString,
    vmwareNFSDatastoreESXName           DisplayString,
    vmwareNFSDatastorePoolName          DisplayString,
    vmwareNFSDatastoreWriteMBps         Unsigned32,
    vmwareNFSDatastoreReadMBps          Unsigned32,
    vmwareNFSDatastoreWriteIops         Unsigned32,
    vmwareNFSDatastoreReadIops          Unsigned32,
    vmwareNFSDatastoreWriteLatency      Unsigned32,
    vmwareNFSDatastoreReadLatency       Unsigned32
}

vmwareNFSDatastoreIndex OBJECT-TYPE
    SYNTAX      Unsigned32
    MAX-ACCESS  not-accessible
    STATUS      current
    DESCRIPTION
    "VMWare NFS Datastore Index."
    ::= { vmwareNFSDatastoreEntry 1 }

vmwareNFSDatastoreVMName OBJECT-TYPE
    SYNTAX      DisplayString
    MAX-ACCESS  read-only
    STATUS      current
    DESCRIPTION
    "VMWare NFS Datastore VM name"
    ::= { vmwareNFSDatastoreEntry 2 }

vmwareNFSDatastoreESXName OBJECT-TYPE
    SYNTAX      DisplayString
    MAX-ACCESS  read-only
    STATUS      current
    DESCRIPTION
    "VMWare NFS Datastore ESX server name"
    ::= { vmwareNFSDatastoreEntry 3 }

vmwareNFSDatastorePoolName OBJECT-TYPE
    SYNTAX      DisplayString
    MAX-ACCESS  read-only
    STATUS      current
    DESCRIPTION
    "VMWare NFS Datastore Pool name"
    ::= { vmwareNFSDatastoreEntry 4 }

vmwareNFSDatastoreWriteMBps OBJECT-TYPE
    SYNTAX         Unsigned32
    MAX-ACCESS     read-only
    STATUS         current
    DESCRIPTION
    "VMWare NFS Datastore writes, MiBs per second"
    ::= { vmwareNFSDatastoreEntry 5 }

vmwareNFSDatastoreReadMBps OBJECT-TYPE
    SYNTAX         Unsigned32
    MAX-ACCESS     read-only
    STATUS         current
    DESCRIPTION
    "VMWare NFS Datastore reads, MiBs per second"
    ::= { vmwareNFSDatastoreEntry 6}

vmwareNFSDatastoreWriteIops OBJECT-TYPE
    SYNTAX         Unsigned32
    MAX-ACCESS     read-only
    STATUS         current
    DESCRIPTION
    "VMWare NFS Datastore reads, IOs per second"
    ::= { vmwareNFSDatastoreEntry 7 }

vmwareNFSDatastoreReadIops OBJECT-TYPE
    SYNTAX         Unsigned32
    MAX-ACCESS     read-only
    STATUS         current
    DESCRIPTION
    "VMWare NFS Datastore reads, IOs per second"
    ::= { vmwareNFSDatastoreEntry 8 }

vmwareNFSDatastoreWriteLatency OBJECT-TYPE
    SYNTAX         Unsigned32
    MAX-ACCESS     read-only
    STATUS         current
    DESCRIPTION
    "VMWare NFS Datastore write latency"
    ::= { vmwareNFSDatastoreEntry 9 }

vmwareNFSDatastoreReadLatency OBJECT-TYPE
    SYNTAX         Unsigned32
    MAX-ACCESS     read-only
    STATUS         current
    DESCRIPTION
    "VMWare NFS Datastore read latency"
    ::= { vmwareNFSDatastoreEntry 10 }

--
-- End of vmwareNFSDatastoreTable
--

--
-- hyperv SMB VMs Table
--
hypervSMBVMsTable OBJECT-TYPE
    SYNTAX         SEQUENCE OF HyperVSMBVMEntry
    MAX-ACCESS     not-accessible
    STATUS         current
    DESCRIPTION
    "HyperV SMB VMs information table"
    ::= { hypervSMBVMs 1 }

hypervSMBVMEntry OBJECT-TYPE
    SYNTAX          HyperVSMBVMEntry
    MAX-ACCESS      not-accessible
    STATUS          current
    DESCRIPTION
    "A row of HyperV SMB VMs information"
    INDEX { hypervSMBVMIndex }
    ::= { hypervSMBVMsTable 1 }

HyperVSMBVMEntry ::= SEQUENCE {
    hypervSMBVMIndex             Unsigned32,
    hypervSMBVMName              DisplayString,
    hypervSMBHyperVName          DisplayString,
    hypervSMBVMPoolName          DisplayString,
    hypervSMBVMWriteMBps         Unsigned32,
    hypervSMBVMReadMBps          Unsigned32,
    hypervSMBVMWriteIops         Unsigned32,
    hypervSMBVMReadIops          Unsigned32,
    hypervSMBVMWriteLatency      Unsigned32,
    hypervSMBVMReadLatency       Unsigned32
}

hypervSMBVMIndex OBJECT-TYPE
    SYNTAX      Unsigned32
    MAX-ACCESS  not-accessible
    STATUS      current
    DESCRIPTION
    "HyperV SMB VM Index."
    ::= { hypervSMBVMEntry 1 }

hypervSMBVMName OBJECT-TYPE
    SYNTAX      DisplayString
    MAX-ACCESS  read-only
    STATUS      current
    DESCRIPTION
    "HyperV SMB VM name"
    ::= { hypervSMBVMEntry 2 }

hypervSMBHyperVName OBJECT-TYPE
    SYNTAX      DisplayString
    MAX-ACCESS  read-only
    STATUS      current
    DESCRIPTION
    "HyperV SMB VM ESX server name"
    ::= { hypervSMBVMEntry 3 }

hypervSMBVMPoolName OBJECT-TYPE
    SYNTAX      DisplayString
    MAX-ACCESS  read-only
    STATUS      current
    DESCRIPTION
    "HyperV SMB VM Pool name"
    ::= { hypervSMBVMEntry 4 }

hypervSMBVMWriteMBps OBJECT-TYPE
    SYNTAX         Unsigned32
    MAX-ACCESS     read-only
    STATUS         current
    DESCRIPTION
    "HyperV SMB VM writes, MiBs per second"
    ::= { hypervSMBVMEntry 5 }

hypervSMBVMReadMBps OBJECT-TYPE
    SYNTAX         Unsigned32
    MAX-ACCESS     read-only
    STATUS         current
    DESCRIPTION
    "HyperV SMB VM reads, MiBs per second"
    ::= { hypervSMBVMEntry 6 }

hypervSMBVMWriteIops OBJECT-TYPE
    SYNTAX         Unsigned32
    MAX-ACCESS     read-only
    STATUS         current
    DESCRIPTION
    "HyperV SMB VM reads, IOs per second"
    ::= { hypervSMBVMEntry 7 }

hypervSMBVMReadIops OBJECT-TYPE
    SYNTAX         Unsigned32
    MAX-ACCESS     read-only
    STATUS         current
    DESCRIPTION
    "HyperV SMB VM reads, IOs per second"
    ::= { hypervSMBVMEntry 8 }

hypervSMBVMWriteLatency OBJECT-TYPE
    SYNTAX         Unsigned32
    MAX-ACCESS     read-only
    STATUS         current
    DESCRIPTION
    "HyperV SMB VM write latency"
    ::= { hypervSMBVMEntry 9 }

hypervSMBVMReadLatency OBJECT-TYPE
    SYNTAX         Unsigned32
    MAX-ACCESS     read-only
    STATUS         current
    DESCRIPTION
    "HyperV SMB VM read latency"
    ::= { hypervSMBVMEntry 10 }

--
-- End of hypervSMBVMTable
--

--
-- haResourcesTable
--
haResourcesTable OBJECT-TYPE
    SYNTAX         SEQUENCE OF HAResourceEntry
    MAX-ACCESS     not-accessible
    STATUS         current
    DESCRIPTION
    "HA Resource information table"
    ::= { haResources 1 }

haResourceEntry OBJECT-TYPE
    SYNTAX          HAResourceEntry
    MAX-ACCESS      not-accessible
    STATUS          current
    DESCRIPTION
    "A row of HA Resource information"
    INDEX { haResourceIndex }
    ::= { haResourcesTable 1 }

HAResourceEntry ::= SEQUENCE {
    haResourceIndex             Unsigned32,
    haResourceName              DisplayString,
    haResourceDescription       DisplayString,
    haResourceStatus            DisplayString,
    haResourceGroup             DisplayString,
    haResourceActiveNode        DisplayString
}

haResourceIndex OBJECT-TYPE
    SYNTAX      Unsigned32
    MAX-ACCESS  not-accessible
    STATUS      current
    DESCRIPTION
    "HA Resource Index."
    ::= { haResourceEntry 1 }

haResourceName OBJECT-TYPE
    SYNTAX      DisplayString
    MAX-ACCESS  read-only
    STATUS      current
    DESCRIPTION
    "HA Resource name"
    ::= { haResourceEntry 2 }

haResourceDescription OBJECT-TYPE
    SYNTAX      DisplayString
    MAX-ACCESS  read-only
    STATUS      current
    DESCRIPTION
    "HA Resource description"
    ::= { haResourceEntry 3 }

haResourceStatus OBJECT-TYPE
    SYNTAX      DisplayString
    MAX-ACCESS  read-only
    STATUS      current
    DESCRIPTION
    "HA Resource status"
    ::= { haResourceEntry 4 }

haResourceGroup OBJECT-TYPE
    SYNTAX      DisplayString
    MAX-ACCESS  read-only
    STATUS      current
    DESCRIPTION
    "HA Resource group"
    ::= { haResourceEntry 5 }

haResourceActiveNode OBJECT-TYPE
    SYNTAX      DisplayString
    MAX-ACCESS  read-only
    STATUS      current
    DESCRIPTION
    "HA Resource active node"
    ::= { haResourceEntry 6 }

--
-- End of haResourcesTable
--

--
-- Network Interface Table
--
nicTable OBJECT-TYPE
    SYNTAX         SEQUENCE OF NICEntry
    MAX-ACCESS     not-accessible
    STATUS         current
    DESCRIPTION
    "NIC information table"
    ::= { networkInterfaces 1 }

nicEntry OBJECT-TYPE
    SYNTAX          NICEntry
    MAX-ACCESS      not-accessible
    STATUS          current
    DESCRIPTION
    "A row of NIC information"
    INDEX { nicIndex }
    ::= { nicTable 1 }

NICEntry ::= SEQUENCE {
    nicIndex                    Unsigned32,
    nicName                     DisplayString,
    nicState                    DisplayString,
    nicGroup                    DisplayString,
    nicMTU                      Unsigned32,
    nicReceiveMbps              Unsigned32,
    nicTransmitMbps             Unsigned32
}

nicIndex OBJECT-TYPE
    SYNTAX      Unsigned32
    MAX-ACCESS  not-accessible
    STATUS      current
    DESCRIPTION
    "NIC Index."
    ::= { nicEntry 1 }

nicName OBJECT-TYPE
    SYNTAX      DisplayString
    MAX-ACCESS  read-only
    STATUS      current
    DESCRIPTION
    "NIC name"
    ::= { nicEntry 2 }

nicState OBJECT-TYPE
    SYNTAX      DisplayString
    MAX-ACCESS  read-only
    STATUS      current
    DESCRIPTION
    "NIC state"
    ::= { nicEntry 3 }

nicGroup OBJECT-TYPE
    SYNTAX      DisplayString
    MAX-ACCESS  read-only
    STATUS      current
    DESCRIPTION
    "NIC group"
    ::= { nicEntry 4 }

nicMTU OBJECT-TYPE
    SYNTAX      Unsigned32
    MAX-ACCESS  read-only
    STATUS      current
    DESCRIPTION
    "NIC maximum transmission unit"
    ::= { nicEntry 5 }

nicReceiveMbps OBJECT-TYPE
    SYNTAX      Unsigned32
    MAX-ACCESS  read-only
    STATUS      current
    DESCRIPTION
    "NIC bytes received in MBs per second"
    ::= { nicEntry 6 }

nicTransmitMbps OBJECT-TYPE
    SYNTAX      Unsigned32
    MAX-ACCESS  read-only
    STATUS      current
    DESCRIPTION
    "NIC bytes received in MBs per second"
    ::= { nicEntry 7 }

--
-- End of nicTable
--

--
-- Link Aggregates Table
--
linkAggregateTable OBJECT-TYPE
    SYNTAX         SEQUENCE OF LinkAggregateEntry
    MAX-ACCESS     not-accessible
    STATUS         current
    DESCRIPTION
    "Link Aggregate information table"
    ::= { linkAggregates 1 }

linkAggregateEntry OBJECT-TYPE
    SYNTAX          LinkAggregateEntry
    MAX-ACCESS      not-accessible
    STATUS          current
    DESCRIPTION
    "A row of LinkAggregate information"
    INDEX { linkAggregateIndex }
    ::= { linkAggregateTable 1 }

LinkAggregateEntry ::= SEQUENCE {
    linkAggregateIndex                    Unsigned32,
    linkAggregateGroupName                DisplayString,
    linkAggregatePorts                    DisplayString,
    linkAggregateOutboundPolicy           DisplayString,
    linkAggregateMode                     DisplayString,
    linkAggregateMTU                      Unsigned32
}

linkAggregateIndex OBJECT-TYPE
    SYNTAX      Unsigned32
    MAX-ACCESS  not-accessible
    STATUS      current
    DESCRIPTION
    "Link aggregate Index."
    ::= { linkAggregateEntry 1 }

linkAggregateGroupName OBJECT-TYPE
    SYNTAX      DisplayString
    MAX-ACCESS  read-only
    STATUS      current
    DESCRIPTION
    "Link aggregate group name"
    ::= { linkAggregateEntry 2 }

linkAggregatePorts OBJECT-TYPE
    SYNTAX      DisplayString
    MAX-ACCESS  read-only
    STATUS      current
    DESCRIPTION
    "Link aggregate ports"
    ::= { linkAggregateEntry 3 }

linkAggregateOutboundPolicy OBJECT-TYPE
    SYNTAX      DisplayString
    MAX-ACCESS  read-only
    STATUS      current
    DESCRIPTION
    "Link aggregate outbouand policy"
    ::= { linkAggregateEntry 4 }

linkAggregateMode OBJECT-TYPE
    SYNTAX      DisplayString
    MAX-ACCESS  read-only
    STATUS      current
    DESCRIPTION
    "Link aggregate mode"
    ::= { linkAggregateEntry 5 }

linkAggregateMTU OBJECT-TYPE
    SYNTAX      Unsigned32
    MAX-ACCESS  read-only
    STATUS      current
    DESCRIPTION
    "Link aggregate maximum transmission unit"
    ::= { linkAggregateEntry 6 }

--
-- End of linkAggregateTable
--

--
-- interfaceGroupTable
--
interfaceGroupTable OBJECT-TYPE
    SYNTAX         SEQUENCE OF InterfaceGroupEntry
    MAX-ACCESS     not-accessible
    STATUS         current
    DESCRIPTION
    "Interface group information table"
    ::= { interfaceGroups 1 }

interfaceGroupEntry OBJECT-TYPE
    SYNTAX          InterfaceGroupEntry
    MAX-ACCESS      not-accessible
    STATUS          current
    DESCRIPTION
    "A row of Interface group information"
    INDEX { interfaceGroupIndex }
    ::= { interfaceGroupTable 1 }

InterfaceGroupEntry ::= SEQUENCE {
    interfaceGroupIndex     Unsigned32,
    interfaceGroupName      DisplayString,
    interfaceGroupVLAN      DisplayString,
    interfaceGroupState     DisplayString
}

interfaceGroupIndex OBJECT-TYPE
    SYNTAX      Unsigned32
    MAX-ACCESS  not-accessible
    STATUS      current
    DESCRIPTION
    "Interface group Index."
    ::= { interfaceGroupEntry 1 }

interfaceGroupName OBJECT-TYPE
    SYNTAX      DisplayString
    MAX-ACCESS  read-only
    STATUS      current
    DESCRIPTION
    "Interface group Name"
    ::= { interfaceGroupEntry 2 }

interfaceGroupVLAN OBJECT-TYPE
    SYNTAX      DisplayString
    MAX-ACCESS  read-only
    STATUS      current
    DESCRIPTION
    "Interface group VLAN id"
    ::= { interfaceGroupEntry 3 }

interfaceGroupState OBJECT-TYPE
    SYNTAX      DisplayString
    MAX-ACCESS  read-only
    STATUS      current
    DESCRIPTION
    "Interface group state"
    ::= { interfaceGroupEntry 4 }

--
-- End of interfaceGroupTable
--

--
-- mappedInterfacesTable
--
mappedInterfacesTable OBJECT-TYPE
    SYNTAX         SEQUENCE OF MappedInterfaceEntry
    MAX-ACCESS     not-accessible
    STATUS         current
    DESCRIPTION
    "Mapping interfaces information table"
    ::= { mappedInterfaces 1 }

mappedInterfaceEntry OBJECT-TYPE
    SYNTAX          MappedInterfaceEntry
    MAX-ACCESS      not-accessible
    STATUS          current
    DESCRIPTION
    "A row of Mapping interface information"
    INDEX { interfaceGroupIndex,
            mappedInterfaceIndex }
    ::= { mappedInterfacesTable 1 }

MappedInterfaceEntry ::= SEQUENCE {
    mappedInterfaceIndex   Unsigned32,
    mappedInterfaceName    DisplayString,
    mappedInterfaceType    DisplayString,
    mappedInterfaceGroup   DisplayString
}

mappedInterfaceIndex OBJECT-TYPE
    SYNTAX      Unsigned32
    MAX-ACCESS  not-accessible
    STATUS      current
    DESCRIPTION
    "Mapping interface Index."
    ::= { mappedInterfaceEntry 1 }

mappedInterfaceName OBJECT-TYPE
    SYNTAX      DisplayString
    MAX-ACCESS  read-only
    STATUS      current
    DESCRIPTION
    "Mapping interface name"
    ::= { mappedInterfaceEntry 2 }

mappedInterfaceType OBJECT-TYPE
    SYNTAX      DisplayString
    MAX-ACCESS  read-only
    STATUS      current
    DESCRIPTION
    "Mapping interface type"
    ::= { mappedInterfaceEntry 3 }

mappedInterfaceGroup OBJECT-TYPE
    SYNTAX      DisplayString
    MAX-ACCESS  read-only
    STATUS      current
    DESCRIPTION
    "Mapping interface group name"
    ::= { mappedInterfaceEntry 4 }

--
-- End of mappedInterfacesTable
--

--
-- physicalInterfacesTable
--
physicalInterfacesTable OBJECT-TYPE
    SYNTAX         SEQUENCE OF PhysicalInterfaceEntry
    MAX-ACCESS     not-accessible
    STATUS         current
    DESCRIPTION
    "Physical interfaces information table"
    ::= { physicalInterfaces 1 }

physicalInterfaceEntry OBJECT-TYPE
    SYNTAX          PhysicalInterfaceEntry
    MAX-ACCESS      not-accessible
    STATUS          current
    DESCRIPTION
    "A row of Physical interface information"
    INDEX { interfaceGroupIndex,
            physicalInterfaceIndex }
    ::= { physicalInterfacesTable 1 }

PhysicalInterfaceEntry ::= SEQUENCE {
    physicalInterfaceIndex              Unsigned32,
    physicalInterfaceAddress            DisplayString,
    physicalInterfaceNetmask            DisplayString,
    physicalInterfaceType               DisplayString,
    physicalInterfaceActiveOn           DisplayString,
    physicalInterfaceFailoverMode       DisplayString,
    physicalInterfaceGroup              DisplayString
}

physicalInterfaceIndex OBJECT-TYPE
    SYNTAX      Unsigned32
    MAX-ACCESS  not-accessible
    STATUS      current
    DESCRIPTION
    "Physical interface Index."
    ::= { physicalInterfaceEntry 1 }

physicalInterfaceAddress OBJECT-TYPE
    SYNTAX      DisplayString
    MAX-ACCESS  read-only
    STATUS      current
    DESCRIPTION
    "Physical interface address"
    ::= { physicalInterfaceEntry 2 }

physicalInterfaceNetmask OBJECT-TYPE
    SYNTAX      DisplayString
    MAX-ACCESS  read-only
    STATUS      current
    DESCRIPTION
    "Physical interface netmask"
    ::= { physicalInterfaceEntry 3 }

physicalInterfaceType OBJECT-TYPE
    SYNTAX      DisplayString
    MAX-ACCESS  read-only
    STATUS      current
    DESCRIPTION
    "Physical interface type"
    ::= { physicalInterfaceEntry 4 }

physicalInterfaceActiveOn OBJECT-TYPE
    SYNTAX      DisplayString
    MAX-ACCESS  read-only
    STATUS      current
    DESCRIPTION
    "Physical interface active on which node"
    ::= { physicalInterfaceEntry 5 }

physicalInterfaceFailoverMode OBJECT-TYPE
    SYNTAX      DisplayString
    MAX-ACCESS  read-only
    STATUS      current
    DESCRIPTION
    "Physical interface failover mode"
    ::= { physicalInterfaceEntry 6 }

physicalInterfaceGroup OBJECT-TYPE
    SYNTAX      DisplayString
    MAX-ACCESS  read-only
    STATUS      current
    DESCRIPTION
    "Physical interface group name"
    ::= { physicalInterfaceEntry 7 }

--
-- End of physicalInterfacesTable
--


--
-- Notifications
--

notificationObjects OBJECT IDENTIFIER ::= { tegileArray-notifications 1 }

notificationProps OBJECT IDENTIFIER ::= { notificationObjects 1 }

notificationDescription OBJECT-TYPE
    SYNTAX      DisplayString
    MAX-ACCESS  read-only
    STATUS      current
    DESCRIPTION
    "Description of the notification."
::= { notificationProps 1 }

notificationTime OBJECT-TYPE
    SYNTAX      DisplayString
    MAX-ACCESS  read-only
    STATUS      current
    DESCRIPTION
    "Time of the notification generated"
::= { notificationProps 2 }

notificationSeverity OBJECT-TYPE
    SYNTAX      DisplayString
    MAX-ACCESS  read-only
    STATUS      current
    DESCRIPTION
    "The severity level of the notification (informational, warning, error, critical)."
::= { notificationProps 3 }

notificationComponentName OBJECT-TYPE
    SYNTAX      DisplayString
    MAX-ACCESS  read-only
    STATUS      current
    DESCRIPTION
    "Name of the component that originated the notification."
::= { notificationProps 4 }

notificationTargetEntityName OBJECT-TYPE
    SYNTAX      DisplayString
    MAX-ACCESS  read-only
    STATUS      current
    DESCRIPTION
    "Name of the Target entity."
::= { notificationProps 5 }

notificationEventCode OBJECT-TYPE
    SYNTAX      DisplayString
    MAX-ACCESS  read-only
    STATUS      current
    DESCRIPTION
    "Description of the notification."
::= { notificationProps 6 }

notificationSensorAction OBJECT-TYPE
    SYNTAX      DisplayString
    MAX-ACCESS  read-only
    STATUS      current
    DESCRIPTION
    "IPMI Sensor action."
::= { notificationProps 7 }

notificationSensorNumber OBJECT-TYPE
    SYNTAX      DisplayString
    MAX-ACCESS  read-only
    STATUS      current
    DESCRIPTION
    "IPMI Sensor number."
::= { notificationProps 8 }

notificationSensorSuspect OBJECT-TYPE
    SYNTAX      DisplayString
    MAX-ACCESS  read-only
    STATUS      current
    DESCRIPTION
    "IPMI Sensor suspect"
::= { notificationProps 9 }

notificationReadingTriggerValue OBJECT-TYPE
    SYNTAX      DisplayString
    MAX-ACCESS  read-only
    STATUS      current
    DESCRIPTION
    "Reading trigger value."
::= { notificationProps 10 }

notificationThresholdTriggerValue OBJECT-TYPE
    SYNTAX      DisplayString
    MAX-ACCESS  read-only
    STATUS      current
    DESCRIPTION
    "Threshold trigger value."
::= { notificationProps 11 }

notificationReadingUnit OBJECT-TYPE
    SYNTAX      DisplayString
    MAX-ACCESS  read-only
    STATUS      current
    DESCRIPTION
    "Reading unit of the value."
::= { notificationProps 12 }


notifications OBJECT IDENTIFIER ::= { notificationObjects 2 }

-- Test notification
testNotification NOTIFICATION-TYPE
    OBJECTS{
        notificationDescription,
        notificationTime,
        notificationSeverity,
        notificationComponentName,
        notificationTargetEntityName,
        notificationEventCode
    }
    STATUS current
    DESCRIPTION
       "Test notification/trap"
::= { notifications 10 }

-- Disk related events
diskIsOnline NOTIFICATION-TYPE
    OBJECTS{
        notificationDescription,
        notificationTime,
        notificationSeverity,
        notificationComponentName,
        notificationTargetEntityName,
        notificationEventCode
    }
    STATUS current
    DESCRIPTION
       "Disk came back online"
::= { notifications 101 }

diskGoneOffline NOTIFICATION-TYPE
    OBJECTS{
        notificationDescription,
        notificationTime,
        notificationSeverity,
        notificationComponentName,
        notificationTargetEntityName,
        notificationEventCode
    }
    STATUS current
    DESCRIPTION
       "Disk went offline"
::= { notifications 102 }

diskError NOTIFICATION-TYPE
    OBJECTS{
        notificationDescription,
        notificationTime,
        notificationSeverity,
        notificationComponentName,
        notificationTargetEntityName,
        notificationEventCode
    }
    STATUS current
    DESCRIPTION
       "Disk error encountered"
::= { notifications 103 }

spareDiskReplaced NOTIFICATION-TYPE
    OBJECTS{
        notificationDescription,
        notificationTime,
        notificationSeverity,
        notificationComponentName,
        notificationTargetEntityName,
        notificationEventCode
    }
    STATUS current
    DESCRIPTION
       "Spare disk replaced"
::= { notifications 104 }

diskSlowIo NOTIFICATION-TYPE
    OBJECTS{
        notificationDescription,
        notificationTime,
        notificationSeverity,
        notificationComponentName,
        notificationTargetEntityName,
        notificationEventCode
    }
    STATUS current
    DESCRIPTION
       "Slow I/O operations observed on Disk"
::= { notifications 105 }

poolDiskReplaced NOTIFICATION-TYPE
    OBJECTS{
        notificationDescription,
        notificationTime,
        notificationSeverity,
        notificationComponentName,
        notificationTargetEntityName,
        notificationEventCode
    }
    STATUS current
    DESCRIPTION
       "Disk replaced with a new disk on a pool"
::= { notifications 106 }

-- Pool related events

poolCreated NOTIFICATION-TYPE
    OBJECTS{
        notificationDescription,
        notificationTime,
        notificationSeverity,
        notificationComponentName,
        notificationTargetEntityName,
        notificationEventCode
    }
    STATUS current
    DESCRIPTION
       "Pool is created"
::= { notifications 201 }

poolDeleted NOTIFICATION-TYPE
    OBJECTS{
        notificationDescription,
        notificationTime,
        notificationSeverity,
        notificationComponentName,
        notificationTargetEntityName,
        notificationEventCode
    }
    STATUS current
    DESCRIPTION
       "Pool is deleted"
::= { notifications 202 }

poolDeletionFailed NOTIFICATION-TYPE
    OBJECTS{
        notificationDescription,
        notificationTime,
        notificationSeverity,
        notificationComponentName,
        notificationTargetEntityName,
        notificationEventCode
    }
    STATUS current
    DESCRIPTION
       "Pool deletion attempt failed"
::= { notifications 203 }

poolExpanded NOTIFICATION-TYPE
    OBJECTS{
        notificationDescription,
        notificationTime,
        notificationSeverity,
        notificationComponentName,
        notificationTargetEntityName,
        notificationEventCode
    }
    STATUS current
    DESCRIPTION
       "Pool is expanded"
::= { notifications 204 }

poolExported NOTIFICATION-TYPE
    OBJECTS{
        notificationDescription,
        notificationTime,
        notificationSeverity,
        notificationComponentName,
        notificationTargetEntityName,
        notificationEventCode
    }
    STATUS current
    DESCRIPTION
       "Pool is exported"
::= { notifications 205 }

poolImported NOTIFICATION-TYPE
    OBJECTS{
        notificationDescription,
        notificationTime,
        notificationSeverity,
        notificationComponentName,
        notificationTargetEntityName,
        notificationEventCode
    }
    STATUS current
    DESCRIPTION
       "Pool is imported"
::= { notifications 206 }

poolUpgraded NOTIFICATION-TYPE
    OBJECTS{
        notificationDescription,
        notificationTime,
        notificationSeverity,
        notificationComponentName,
        notificationTargetEntityName,
        notificationEventCode
    }
    STATUS current
    DESCRIPTION
       "Pool is upgraded"
::= { notifications 207 }

poolQuotaExceedThresholdWarning NOTIFICATION-TYPE
    OBJECTS{
        notificationDescription,
        notificationTime,
        notificationSeverity,
        notificationComponentName,
        notificationTargetEntityName,
        notificationEventCode
    }
    STATUS current
    DESCRIPTION
       "Pool quota exceeded the threshold limit"
::= { notifications 208 }

poolMetaDataQuotaExceedThresholdWarning NOTIFICATION-TYPE
    OBJECTS{
        notificationDescription,
        notificationTime,
        notificationSeverity,
        notificationComponentName,
        notificationTargetEntityName,
        notificationEventCode
    }
    STATUS current
    DESCRIPTION
       "Pool meta-data quota exceeded the threshold limit"
::= { notifications 209 }

poolAvailableMetaToDataRatioBelowThresholdWarning NOTIFICATION-TYPE
    OBJECTS{
        notificationDescription,
        notificationTime,
        notificationSeverity,
        notificationComponentName,
        notificationTargetEntityName,
        notificationEventCode
    }
    STATUS current
    DESCRIPTION
       "Pool available meta-data to data ratio below threshold limit"
::= { notifications 210 }

poolQuotaFinished NOTIFICATION-TYPE
    OBJECTS{
        notificationDescription,
        notificationTime,
        notificationSeverity,
        notificationComponentName,
        notificationTargetEntityName,
        notificationEventCode
    }
    STATUS current
    DESCRIPTION
       "Pool quota finished"
::= { notifications 211 }

poolDegraded NOTIFICATION-TYPE
    OBJECTS{
        notificationDescription,
        notificationTime,
        notificationSeverity,
        notificationComponentName,
        notificationTargetEntityName,
        notificationEventCode
    }
    STATUS current
    DESCRIPTION
       "Pool has degraded"
::= { notifications 212 }

-- Project related events
projectCreatedSuccessfully NOTIFICATION-TYPE
    OBJECTS{
        notificationDescription,
        notificationTime,
        notificationSeverity,
        notificationComponentName,
        notificationTargetEntityName,
        notificationEventCode
    }
    STATUS current
    DESCRIPTION
       "Project created successfully"
::= { notifications 301 }

projectDeletionFailed NOTIFICATION-TYPE
    OBJECTS{
        notificationDescription,
        notificationTime,
        notificationSeverity,
        notificationComponentName,
        notificationTargetEntityName,
        notificationEventCode
    }
    STATUS current
    DESCRIPTION
       "Project deleted failed"
::= { notifications 302 }

projectDeleted NOTIFICATION-TYPE
    OBJECTS{
        notificationDescription,
        notificationTime,
        notificationSeverity,
        notificationComponentName,
        notificationTargetEntityName,
        notificationEventCode
    }
    STATUS current
    DESCRIPTION
       "Project is deleted"
::= { notifications 303 }

projectModified NOTIFICATION-TYPE
    OBJECTS{
        notificationDescription,
        notificationTime,
        notificationSeverity,
        notificationComponentName,
        notificationTargetEntityName,
        notificationEventCode
    }
    STATUS current
    DESCRIPTION
       "Project is modified"
::= { notifications 304 }

projectThresholdExceedWarning NOTIFICATION-TYPE
    OBJECTS{
        notificationDescription,
        notificationTime,
        notificationSeverity,
        notificationComponentName,
        notificationTargetEntityName,
        notificationEventCode
    }
    STATUS current
    DESCRIPTION
       "Project usage has exceeded threshold."
::= { notifications 305 }

projectQuotaFinished NOTIFICATION-TYPE
    OBJECTS{
        notificationDescription,
        notificationTime,
        notificationSeverity,
        notificationComponentName,
        notificationTargetEntityName,
        notificationEventCode
    }
    STATUS current
    DESCRIPTION
       "Project quota is finished."
::= { notifications 306 }

projectCreatedWithNonOptimalBlockSize NOTIFICATION-TYPE
    OBJECTS{
        notificationDescription,
        notificationTime,
        notificationSeverity,
        notificationComponentName,
        notificationTargetEntityName,
        notificationEventCode
    }
    STATUS current
    DESCRIPTION
       "Project created with non optimal block size"
::= { notifications 307 }

-- Volume related events
volumeCreatedSuccessfully NOTIFICATION-TYPE
    OBJECTS{
        notificationDescription,
        notificationTime,
        notificationSeverity,
        notificationComponentName,
        notificationTargetEntityName,
        notificationEventCode
    }
    STATUS current
    DESCRIPTION
       "Volume created successfully"
::= { notifications 401 }

volumeModifyCompleted NOTIFICATION-TYPE
    OBJECTS{
        notificationDescription,
        notificationTime,
        notificationSeverity,
        notificationComponentName,
        notificationTargetEntityName,
        notificationEventCode
    }
    STATUS current
    DESCRIPTION
       "Volume is modified"
::= { notifications 402 }

volumeDeleteCompleted NOTIFICATION-TYPE
    OBJECTS{
        notificationDescription,
        notificationTime,
        notificationSeverity,
        notificationComponentName,
        notificationTargetEntityName,
        notificationEventCode
    }
    STATUS current
    DESCRIPTION
       "Volume is deleted"
::= { notifications 403 }

volumeDeleteFailed NOTIFICATION-TYPE
    OBJECTS{
        notificationDescription,
        notificationTime,
        notificationSeverity,
        notificationComponentName,
        notificationTargetEntityName,
        notificationEventCode
    }
    STATUS current
    DESCRIPTION
       "Volume deletion failed"
::= { notifications 404 }

volumeExceedsThresholdWarning NOTIFICATION-TYPE
    OBJECTS{
        notificationDescription,
        notificationTime,
        notificationSeverity,
        notificationComponentName,
        notificationTargetEntityName,
        notificationEventCode
    }
    STATUS current
    DESCRIPTION
       "Volume Quota has exceeded the configured Limit"
::= { notifications 405 }

volumeQuotaFinished NOTIFICATION-TYPE
    OBJECTS{
        notificationDescription,
        notificationTime,
        notificationSeverity,
        notificationComponentName,
        notificationTargetEntityName,
        notificationEventCode
    }
    STATUS current
    DESCRIPTION
       "Volume Quota has Finished"
::= { notifications 406}

volumeCreatedWithNonOptimalBlockSize NOTIFICATION-TYPE
    OBJECTS{
        notificationDescription,
        notificationTime,
        notificationSeverity,
        notificationComponentName,
        notificationTargetEntityName,
        notificationEventCode
    }
    STATUS current
    DESCRIPTION
       "Volume created with non optimal block size"
::= { notifications 407 }

volumeOnline NOTIFICATION-TYPE
    OBJECTS{
        notificationDescription,
        notificationTime,
        notificationSeverity,
        notificationComponentName,
        notificationTargetEntityName,
        notificationEventCode
    }
    STATUS current
    DESCRIPTION
       "Volume came back online"
::= { notifications 408}

volumeOffline NOTIFICATION-TYPE
    OBJECTS{
        notificationDescription,
        notificationTime,
        notificationSeverity,
        notificationComponentName,
        notificationTargetEntityName,
        notificationEventCode
    }
    STATUS current
    DESCRIPTION
       "Volume went offline"
::= { notifications 409 }

-- Share related events
shareCreatedSuccessfully NOTIFICATION-TYPE
    OBJECTS{
        notificationDescription,
        notificationTime,
        notificationSeverity,
        notificationComponentName,
        notificationTargetEntityName,
        notificationEventCode
    }
    STATUS current
    DESCRIPTION
       "Share created successfully"
::= { notifications 501 }

shareDeletionFailed NOTIFICATION-TYPE
    OBJECTS{
        notificationDescription,
        notificationTime,
        notificationSeverity,
        notificationComponentName,
        notificationTargetEntityName,
        notificationEventCode
    }
    STATUS current
    DESCRIPTION
       "Share deletion failed"
::= { notifications 502 }

shareDeleted NOTIFICATION-TYPE
    OBJECTS{
        notificationDescription,
        notificationTime,
        notificationSeverity,
        notificationComponentName,
        notificationTargetEntityName,
        notificationEventCode
    }
    STATUS current
    DESCRIPTION
       "Share is deleted"
::= { notifications 503 }

shareExceedThresholdWarning NOTIFICATION-TYPE
    OBJECTS{
        notificationDescription,
        notificationTime,
        notificationSeverity,
        notificationComponentName,
        notificationTargetEntityName,
        notificationEventCode
    }
    STATUS current
    DESCRIPTION
       "Share exceeds the threshold limit"
::= { notifications 504 }

shareQuotaFinished NOTIFICATION-TYPE
    OBJECTS{
        notificationDescription,
        notificationTime,
        notificationSeverity,
        notificationComponentName,
        notificationTargetEntityName,
        notificationEventCode
    }
    STATUS current
    DESCRIPTION
       "Share quota is finished"
::= { notifications 505 }

shareCreatedWithNonOptimalBlockSize NOTIFICATION-TYPE
    OBJECTS{
        notificationDescription,
        notificationTime,
        notificationSeverity,
        notificationComponentName,
        notificationTargetEntityName,
        notificationEventCode
    }
    STATUS current
    DESCRIPTION
       "Share created with non optimal block size"
::= { notifications 506 }

shareModified NOTIFICATION-TYPE
    OBJECTS{
        notificationDescription,
        notificationTime,
        notificationSeverity,
        notificationComponentName,
        notificationTargetEntityName,
        notificationEventCode
    }
    STATUS current
    DESCRIPTION
       "Share properties are modfied"
::= { notifications 507 }

-- ACL events
aclMigrationStarted NOTIFICATION-TYPE
    OBJECTS{
        notificationDescription,
        notificationTime,
        notificationSeverity,
        notificationComponentName,
        notificationTargetEntityName,
        notificationEventCode
    }
    STATUS current
    DESCRIPTION
       "ACL migration started"
::= { notifications 601 }

aclMigrationCompleted NOTIFICATION-TYPE
    OBJECTS{
        notificationDescription,
        notificationTime,
        notificationSeverity,
        notificationComponentName,
        notificationTargetEntityName,
        notificationEventCode
    }
    STATUS current
    DESCRIPTION
       "ACL migration completed"
::= { notifications 602 }

-- Folder related events
deleteFolderCompleted NOTIFICATION-TYPE
    OBJECTS{
        notificationDescription,
        notificationTime,
        notificationSeverity,
        notificationComponentName,
        notificationTargetEntityName,
        notificationEventCode
    }
    STATUS current
    DESCRIPTION
       "Folder deleted"
::= { notifications 701 }

deleteFolderFailed NOTIFICATION-TYPE
    OBJECTS{
        notificationDescription,
        notificationTime,
        notificationSeverity,
        notificationComponentName,
        notificationTargetEntityName,
        notificationEventCode
    }
    STATUS current
    DESCRIPTION
       "Folder deletion failed"
::= { notifications 702 }

-- Snapshot related events
snapshotCreatedSuccessfully NOTIFICATION-TYPE
    OBJECTS{
        notificationDescription,
        notificationTime,
        notificationSeverity,
        notificationComponentName,
        notificationTargetEntityName,
        notificationEventCode
    }
    STATUS current
    DESCRIPTION
       "Snapshot created successfully"
::= { notifications 801 }

snapshotCreationFailed NOTIFICATION-TYPE
    OBJECTS{
        notificationDescription,
        notificationTime,
        notificationSeverity,
        notificationComponentName,
        notificationTargetEntityName,
        notificationEventCode
    }
    STATUS current
    DESCRIPTION
       "Snapshot creation failed"
::= { notifications 802 }

snapshotDeletedSuccessfully NOTIFICATION-TYPE
    OBJECTS{
        notificationDescription,
        notificationTime,
        notificationSeverity,
        notificationComponentName,
        notificationTargetEntityName,
        notificationEventCode
    }
    STATUS current
    DESCRIPTION
       "Snapshot deleted successfully"
::= { notifications 803 }

snapshotDeleteFailed NOTIFICATION-TYPE
    OBJECTS{
        notificationDescription,
        notificationTime,
        notificationSeverity,
        notificationComponentName,
        notificationTargetEntityName,
        notificationEventCode
    }
    STATUS current
    DESCRIPTION
       "Snapshot deletion failed"
::= { notifications 804 }

snapshotCloningFailed NOTIFICATION-TYPE
    OBJECTS{
        notificationDescription,
        notificationTime,
        notificationSeverity,
        notificationComponentName,
        notificationTargetEntityName,
        notificationEventCode
    }
    STATUS current
    DESCRIPTION
       "Snapshot cloning failed"
::= { notifications 805 }

snapshotCloneCompleted NOTIFICATION-TYPE
    OBJECTS{
        notificationDescription,
        notificationTime,
        notificationSeverity,
        notificationComponentName,
        notificationTargetEntityName,
        notificationEventCode
    }
    STATUS current
    DESCRIPTION
       "Snapshot clone completed"
::= { notifications 806 }

snapshotRollbackFailed NOTIFICATION-TYPE
    OBJECTS{
        notificationDescription,
        notificationTime,
        notificationSeverity,
        notificationComponentName,
        notificationTargetEntityName,
        notificationEventCode
    }
    STATUS current
    DESCRIPTION
       "Snapshot rollback failed"
::= { notifications 807 }

snapshotRollbackCompleted NOTIFICATION-TYPE
    OBJECTS{
        notificationDescription,
        notificationTime,
        notificationSeverity,
        notificationComponentName,
        notificationTargetEntityName,
        notificationEventCode
    }
    STATUS current
    DESCRIPTION
       "Snapshot rollback completed"
::= { notifications 808 }

-- HA related events
haResourceGroupTakeBackCompleted NOTIFICATION-TYPE
    OBJECTS{
        notificationDescription,
        notificationTime,
        notificationSeverity,
        notificationComponentName,
        notificationTargetEntityName,
        notificationEventCode
    }
    STATUS current
    DESCRIPTION
       "HA resource group taken back"
::= { notifications 901 }

haResourceGroupTakeOverCompleted NOTIFICATION-TYPE
    OBJECTS{
        notificationDescription,
        notificationTime,
        notificationSeverity,
        notificationComponentName,
        notificationTargetEntityName,
        notificationEventCode
    }
    STATUS current
    DESCRIPTION
       "HA resource group taken over"
::= { notifications 902 }

-- Peer events
controllerUp NOTIFICATION-TYPE
    OBJECTS{
        notificationDescription,
        notificationTime,
        notificationSeverity,
        notificationComponentName,
        notificationTargetEntityName,
        notificationEventCode
    }
    STATUS current
    DESCRIPTION
       "Controller is now up"
::= { notifications 1001 }

controllerDown NOTIFICATION-TYPE
    OBJECTS{
        notificationDescription,
        notificationTime,
        notificationSeverity,
        notificationComponentName,
        notificationTargetEntityName,
        notificationEventCode
    }
    STATUS current
    DESCRIPTION
       "Controller went down"
::= { notifications 1002 }

intelliFlashSoftwareUp NOTIFICATION-TYPE
    OBJECTS{
        notificationDescription,
        notificationTime,
        notificationSeverity,
        notificationComponentName,
        notificationTargetEntityName,
        notificationEventCode
    }
    STATUS current
    DESCRIPTION
       "IntelliFlash is now up on controller"
::= { notifications 1003 }

intelliFlashSoftwareDown NOTIFICATION-TYPE
    OBJECTS{
        notificationDescription,
        notificationTime,
        notificationSeverity,
        notificationComponentName,
        notificationTargetEntityName,
        notificationEventCode
    }
    STATUS current
    DESCRIPTION
       "IntelliFlash went down on controller"
::= { notifications 1004 }

controllerTimeDrift NOTIFICATION-TYPE
    OBJECTS{
        notificationDescription,
        notificationTime,
        notificationSeverity,
        notificationComponentName,
        notificationTargetEntityName,
        notificationEventCode
    }
    STATUS current
    DESCRIPTION
       "Controllers Time drift detected"
::= { notifications 1005 }

-- FC related events
fcInitiatorCreateCompleted NOTIFICATION-TYPE
    OBJECTS{
        notificationDescription,
        notificationTime,
        notificationSeverity,
        notificationComponentName,
        notificationTargetEntityName,
        notificationEventCode
    }
    STATUS current
    DESCRIPTION
       "FC initiator created"
::= { notifications 1101 }

fcInitiatorCreateFailed NOTIFICATION-TYPE
    OBJECTS{
        notificationDescription,
        notificationTime,
        notificationSeverity,
        notificationComponentName,
        notificationTargetEntityName,
        notificationEventCode
    }
    STATUS current
    DESCRIPTION
       "FC initiator creation failed"
::= { notifications 1102 }

fcTargetResetHbaPortCompleted NOTIFICATION-TYPE
    OBJECTS{
        notificationDescription,
        notificationTime,
        notificationSeverity,
        notificationComponentName,
        notificationTargetEntityName,
        notificationEventCode
    }
    STATUS current
    DESCRIPTION
       "FC Target HBA Port reset successfully"
::= { notifications 1103 }

fcTargetResetHbaPortFailed NOTIFICATION-TYPE
    OBJECTS{
        notificationDescription,
        notificationTime,
        notificationSeverity,
        notificationComponentName,
        notificationTargetEntityName,
        notificationEventCode
    }
    STATUS current
    DESCRIPTION
       "FC Target HBA Port reset failed"
::= { notifications 1104 }

fcPortOnline NOTIFICATION-TYPE
    OBJECTS{
        notificationDescription,
        notificationTime,
        notificationSeverity,
        notificationComponentName,
        notificationTargetEntityName,
        notificationEventCode
    }
    STATUS current
    DESCRIPTION
       "FC Port is online"
::= { notifications 1105 }

fcPortOffline NOTIFICATION-TYPE
    OBJECTS{
        notificationDescription,
        notificationTime,
        notificationSeverity,
        notificationComponentName,
        notificationTargetEntityName,
        notificationEventCode
    }
    STATUS current
    DESCRIPTION
       "FC Port is offline"
::= { notifications 1106 }

-- Host group related events
initiatorGroupCreateCompleted NOTIFICATION-TYPE
    OBJECTS{
        notificationDescription,
        notificationTime,
        notificationSeverity,
        notificationComponentName,
        notificationTargetEntityName,
        notificationEventCode
    }
    STATUS current
    DESCRIPTION
       "Initiator Group created"
::= { notifications 1201 }

initiatorGroupMemberAdded NOTIFICATION-TYPE
    OBJECTS{
        notificationDescription,
        notificationTime,
        notificationSeverity,
        notificationComponentName,
        notificationTargetEntityName,
        notificationEventCode
    }
    STATUS current
    DESCRIPTION
       "Member added to the Initiator Group"
::= { notifications 1202 }

initiatorGroupMemberRemoved NOTIFICATION-TYPE
    OBJECTS{
        notificationDescription,
        notificationTime,
        notificationSeverity,
        notificationComponentName,
        notificationTargetEntityName,
        notificationEventCode
    }
    STATUS current
    DESCRIPTION
       "Member removed from the Initiator Group"
::= { notifications 1203 }

initiatorGroupDeleteCompleted NOTIFICATION-TYPE
    OBJECTS{
        notificationDescription,
        notificationTime,
        notificationSeverity,
        notificationComponentName,
        notificationTargetEntityName,
        notificationEventCode
    }
    STATUS current
    DESCRIPTION
       "Initiator Group deleted"
::= { notifications 1204 }

-- iSCSI related events
iscsiInitiatorCreateCompleted NOTIFICATION-TYPE
    OBJECTS{
        notificationDescription,
        notificationTime,
        notificationSeverity,
        notificationComponentName,
        notificationTargetEntityName,
        notificationEventCode
    }
    STATUS current
    DESCRIPTION
       "iSCSI initiator created"
::= { notifications 1301 }

iscsiInitiatorCreateFailed NOTIFICATION-TYPE
    OBJECTS{
        notificationDescription,
        notificationTime,
        notificationSeverity,
        notificationComponentName,
        notificationTargetEntityName,
        notificationEventCode
    }
    STATUS current
    DESCRIPTION
       "iSCSI initiator creation failed"
::= { notifications 1302 }

iscsiInitiatorModifyCompleted NOTIFICATION-TYPE
    OBJECTS{
        notificationDescription,
        notificationTime,
        notificationSeverity,
        notificationComponentName,
        notificationTargetEntityName,
        notificationEventCode
    }
    STATUS current
    DESCRIPTION
       "iSCSI initiator properties modified"
::= { notifications 1303 }

iscsiInitiatorDeleteCompleted NOTIFICATION-TYPE
    OBJECTS{
        notificationDescription,
        notificationTime,
        notificationSeverity,
        notificationComponentName,
        notificationTargetEntityName,
        notificationEventCode
    }
    STATUS current
    DESCRIPTION
       "iSCSI initiator deleted"
::= { notifications 1304 }

iscsiTargetCreateCompleted NOTIFICATION-TYPE
    OBJECTS{
        notificationDescription,
        notificationTime,
        notificationSeverity,
        notificationComponentName,
        notificationTargetEntityName,
        notificationEventCode
    }
    STATUS current
    DESCRIPTION
       "iSCSI target created"
::= { notifications 1305 }

iscsiTargetModifyCompleted NOTIFICATION-TYPE
    OBJECTS{
        notificationDescription,
        notificationTime,
        notificationSeverity,
        notificationComponentName,
        notificationTargetEntityName,
        notificationEventCode
    }
    STATUS current
    DESCRIPTION
       "iSCSI target properties modified"
::= { notifications 1306 }

iscsiTargetDeleteCompleted NOTIFICATION-TYPE
    OBJECTS{
        notificationDescription,
        notificationTime,
        notificationSeverity,
        notificationComponentName,
        notificationTargetEntityName,
        notificationEventCode
    }
    STATUS current
    DESCRIPTION
       "iSCSI Target deleted"
::= { notifications 1307 }

iscsiTargetError NOTIFICATION-TYPE
    OBJECTS{
        notificationDescription,
        notificationTime,
        notificationSeverity,
        notificationComponentName,
        notificationTargetEntityName,
        notificationEventCode
    }
    STATUS current
    DESCRIPTION
       "iSCSI target error"
::= { notifications 1308 }

iscsiTargetGroupError NOTIFICATION-TYPE
    OBJECTS{
        notificationDescription,
        notificationTime,
        notificationSeverity,
        notificationComponentName,
        notificationTargetEntityName,
        notificationEventCode
    }
    STATUS current
    DESCRIPTION
       "iSCSI target group error"
::= { notifications 1309 }

iscsiImproperTargetGroup NOTIFICATION-TYPE
    OBJECTS{
        notificationDescription,
        notificationTime,
        notificationSeverity,
        notificationComponentName,
        notificationTargetEntityName,
        notificationEventCode
    }
    STATUS current
    DESCRIPTION
       "iSCSI improper target group error"
::= { notifications 1310 }

-- Target group related events
targetGroupCreateCompleted NOTIFICATION-TYPE
    OBJECTS{
        notificationDescription,
        notificationTime,
        notificationSeverity,
        notificationComponentName,
        notificationTargetEntityName,
        notificationEventCode
    }
    STATUS current
    DESCRIPTION
       "Target group created"
::= { notifications 1401 }

targetGroupMemberAdded NOTIFICATION-TYPE
    OBJECTS{
        notificationDescription,
        notificationTime,
        notificationSeverity,
        notificationComponentName,
        notificationTargetEntityName,
        notificationEventCode
    }
    STATUS current
    DESCRIPTION
       "Member added to the Target group"
::= { notifications 1402 }

targetGroupMemberRemoved NOTIFICATION-TYPE
    OBJECTS{
        notificationDescription,
        notificationTime,
        notificationSeverity,
        notificationComponentName,
        notificationTargetEntityName,
        notificationEventCode
    }
    STATUS current
    DESCRIPTION
       "Member removed from the Target group"
::= { notifications 1403 }

targetGroupDeleteCompleted NOTIFICATION-TYPE
    OBJECTS{
        notificationDescription,
        notificationTime,
        notificationSeverity,
        notificationComponentName,
        notificationTargetEntityName,
        notificationEventCode
    }
    STATUS current
    DESCRIPTION
       "Target group deleted"
::= { notifications 1404 }

-- Array events
adServerTimeDrift NOTIFICATION-TYPE
    OBJECTS{
        notificationDescription,
        notificationTime,
        notificationSeverity,
        notificationComponentName,
        notificationTargetEntityName,
        notificationEventCode
    }
    STATUS current
    DESCRIPTION
       "AD server time drift detected"
::= { notifications 1501 }

maintenanceModeEnabled NOTIFICATION-TYPE
    OBJECTS{
        notificationDescription,
        notificationTime,
        notificationSeverity,
        notificationComponentName,
        notificationTargetEntityName,
        notificationEventCode
    }
    STATUS current
    DESCRIPTION
       "Maintenance mode enabled"
::= { notifications 1502 }

maintenanceModeDisabled NOTIFICATION-TYPE
    OBJECTS{
        notificationDescription,
        notificationTime,
        notificationSeverity,
        notificationComponentName,
        notificationTargetEntityName,
        notificationEventCode
    }
    STATUS current
    DESCRIPTION
       "Maintenance mode disabled"
::= { notifications 1503 }

diagnosticDataUploaded NOTIFICATION-TYPE
    OBJECTS{
        notificationDescription,
        notificationTime,
        notificationSeverity,
        notificationComponentName,
        notificationTargetEntityName,
        notificationEventCode
    }
    STATUS current
    DESCRIPTION
       "Diagnostics data uploaded"
::= { notifications 1504 }

diagnosticDataUploadingFailed NOTIFICATION-TYPE
    OBJECTS{
        notificationDescription,
        notificationTime,
        notificationSeverity,
        notificationComponentName,
        notificationTargetEntityName,
        notificationEventCode
    }
    STATUS current
    DESCRIPTION
       "Diagnostics data upload failed"
::= { notifications 1505 }

alertsCleanupCompleted NOTIFICATION-TYPE
    OBJECTS{
        notificationDescription,
        notificationTime,
        notificationSeverity,
        notificationComponentName,
        notificationTargetEntityName,
        notificationEventCode
    }
    STATUS current
    DESCRIPTION
       "Alerts clean-up completed"
::= { notifications 1506 }

dnsServersUnreachable NOTIFICATION-TYPE
    OBJECTS{
        notificationDescription,
        notificationTime,
        notificationSeverity,
        notificationComponentName,
        notificationTargetEntityName,
        notificationEventCode
    }
    STATUS current
    DESCRIPTION
       "Some DNS Servers are unreachable"
::= { notifications 1507 }

allDnsServersUnreachable NOTIFICATION-TYPE
    OBJECTS{
        notificationDescription,
        notificationTime,
        notificationSeverity,
        notificationComponentName,
        notificationTargetEntityName,
        notificationEventCode
    }
    STATUS current
    DESCRIPTION
       "All configured DNS Servers unreachable"
::= { notifications 1508 }

userLoginFailed NOTIFICATION-TYPE
    OBJECTS{
        notificationDescription,
        notificationTime,
        notificationSeverity,
        notificationComponentName,
        notificationTargetEntityName,
        notificationEventCode
    }
    STATUS current
    DESCRIPTION
       "User login attempt failed."
::= { notifications 1509 }

ntpServerTimeDrift NOTIFICATION-TYPE
    OBJECTS{
        notificationDescription,
        notificationTime,
        notificationSeverity,
        notificationComponentName,
        notificationTargetEntityName,
        notificationEventCode
    }
    STATUS current
    DESCRIPTION
       "Time drift detected between NTP Server and Controller."
::= { notifications 1510 }

intellishellSessionStarted NOTIFICATION-TYPE
    OBJECTS{
        notificationDescription,
        notificationTime,
        notificationSeverity,
        notificationComponentName,
        notificationTargetEntityName,
        notificationEventCode
    }
    STATUS current
    DESCRIPTION
       "IntelliShell Session started."
::= { notifications 1511 }

intellishellSessionEnded NOTIFICATION-TYPE
    OBJECTS{
        notificationDescription,
        notificationTime,
        notificationSeverity,
        notificationComponentName,
        notificationTargetEntityName,
        notificationEventCode
    }
    STATUS current
    DESCRIPTION
       "IntelliShell Session ended."
::= { notifications 1512 }

-- SMB related events
smbSocketFailure NOTIFICATION-TYPE
    OBJECTS{
        notificationDescription,
        notificationTime,
        notificationSeverity,
        notificationComponentName,
        notificationTargetEntityName,
        notificationEventCode
    }
    STATUS current
    DESCRIPTION
       "SMB socket failure detected"
::= { notifications 1601 }

netbiosSocketFailure NOTIFICATION-TYPE
    OBJECTS{
        notificationDescription,
        notificationTime,
        notificationSeverity,
        notificationComponentName,
        notificationTargetEntityName,
        notificationEventCode
    }
    STATUS current
    DESCRIPTION
       "NetBIOS socket failure detected"
::= { notifications 1602 }

-- Upgrade related events
upgradeStarted NOTIFICATION-TYPE
    OBJECTS{
        notificationDescription,
        notificationTime,
        notificationSeverity,
        notificationComponentName,
        notificationTargetEntityName,
        notificationEventCode
    }
    STATUS current
    DESCRIPTION
       "Software upgrade started"
::= { notifications 1701 }

upgradeCompleted NOTIFICATION-TYPE
    OBJECTS{
        notificationDescription,
        notificationTime,
        notificationSeverity,
        notificationComponentName,
        notificationTargetEntityName,
        notificationEventCode
    }
    STATUS current
    DESCRIPTION
       "Software upgrade completed"
::= { notifications 1702 }

upgradeFailed NOTIFICATION-TYPE
    OBJECTS{
        notificationDescription,
        notificationTime,
        notificationSeverity,
        notificationComponentName,
        notificationTargetEntityName,
        notificationEventCode
    }
    STATUS current
    DESCRIPTION
       "Software upgrade failed"
::= { notifications 1703 }

upgradeTimeout NOTIFICATION-TYPE
    OBJECTS{
        notificationDescription,
        notificationTime,
        notificationSeverity,
        notificationComponentName,
        notificationTargetEntityName,
        notificationEventCode
    }
    STATUS current
    DESCRIPTION
       "Software upgrade timed out"
::= { notifications 1704 }

upgradeCantProcessFilesManually NOTIFICATION-TYPE
    OBJECTS{
        notificationDescription,
        notificationTime,
        notificationSeverity,
        notificationComponentName,
        notificationTargetEntityName,
        notificationEventCode
    }
    STATUS current
    DESCRIPTION
       "Software upgrade cannot process files manually"
::= { notifications 1705 }

upgradeDownloadStarted NOTIFICATION-TYPE
    OBJECTS{
        notificationDescription,
        notificationTime,
        notificationSeverity,
        notificationComponentName,
        notificationTargetEntityName,
        notificationEventCode
    }
    STATUS current
    DESCRIPTION
       "Software download started"
::= { notifications 1706 }

upgradeDownloadCompleted NOTIFICATION-TYPE
    OBJECTS{
        notificationDescription,
        notificationTime,
        notificationSeverity,
        notificationComponentName,
        notificationTargetEntityName,
        notificationEventCode
    }
    STATUS current
    DESCRIPTION
       "Software download complete"
::= { notifications 1707 }

upgradeDownloadFailed NOTIFICATION-TYPE
    OBJECTS{
        notificationDescription,
        notificationTime,
        notificationSeverity,
        notificationComponentName,
        notificationTargetEntityName,
        notificationEventCode
    }
    STATUS current
    DESCRIPTION
       "Software download failed"
::= { notifications 1708 }

tdpsUpgradeCompleted NOTIFICATION-TYPE
    OBJECTS{
        notificationDescription,
        notificationTime,
        notificationSeverity,
        notificationComponentName,
        notificationTargetEntityName,
        notificationEventCode
    }
    STATUS current
    DESCRIPTION
       "TDPS upgrade completed"
::= { notifications 1709 }

tdpsUpgradeFailed NOTIFICATION-TYPE
    OBJECTS{
        notificationDescription,
        notificationTime,
        notificationSeverity,
        notificationComponentName,
        notificationTargetEntityName,
        notificationEventCode
    }
    STATUS current
    DESCRIPTION
       "TDPS upgrade failed"
::= { notifications 1710 }

tdpsUpgradeTimeout NOTIFICATION-TYPE
    OBJECTS{
        notificationDescription,
        notificationTime,
        notificationSeverity,
        notificationComponentName,
        notificationTargetEntityName,
        notificationEventCode
    }
    STATUS current
    DESCRIPTION
       "TDPS upgrade timed out"
::= { notifications 1711 }

tdpsUpgradeDownloadStarted NOTIFICATION-TYPE
    OBJECTS{
        notificationDescription,
        notificationTime,
        notificationSeverity,
        notificationComponentName,
        notificationTargetEntityName,
        notificationEventCode
    }
    STATUS current
    DESCRIPTION
       "TDPS download started"
::= { notifications 1712 }

tdpsUpgradeDownloadCompleted NOTIFICATION-TYPE
    OBJECTS{
        notificationDescription,
        notificationTime,
        notificationSeverity,
        notificationComponentName,
        notificationTargetEntityName,
        notificationEventCode
    }
    STATUS current
    DESCRIPTION
       "TDPS download completed"
::= { notifications 1713 }

tdpsUpgradeDownloadFailed NOTIFICATION-TYPE
    OBJECTS{
        notificationDescription,
        notificationTime,
        notificationSeverity,
        notificationComponentName,
        notificationTargetEntityName,
        notificationEventCode
    }
    STATUS current
    DESCRIPTION
       "TDPS download failed"
::= { notifications 1714 }

webdocsUpgradeDownloadStarted NOTIFICATION-TYPE
    OBJECTS{
        notificationDescription,
        notificationTime,
        notificationSeverity,
        notificationComponentName,
        notificationTargetEntityName,
        notificationEventCode
    }
    STATUS current
    DESCRIPTION
       "Webdocs upgrade download started"
::= { notifications 1715 }

webdocsUpgradeDownloadCompleted NOTIFICATION-TYPE
    OBJECTS{
        notificationDescription,
        notificationTime,
        notificationSeverity,
        notificationComponentName,
        notificationTargetEntityName,
        notificationEventCode
    }
    STATUS current
    DESCRIPTION
       "Webdocs upgrade download completed"
::= { notifications 1716 }

webdocsUpgradeDownloadFailed NOTIFICATION-TYPE
    OBJECTS{
        notificationDescription,
        notificationTime,
        notificationSeverity,
        notificationComponentName,
        notificationTargetEntityName,
        notificationEventCode
    }
    STATUS current
    DESCRIPTION
       "Webdocs upgrade download failed"
::= { notifications 1717 }

webdocsUpgradeCompleted NOTIFICATION-TYPE
    OBJECTS{
        notificationDescription,
        notificationTime,
        notificationSeverity,
        notificationComponentName,
        notificationTargetEntityName,
        notificationEventCode
    }
    STATUS current
    DESCRIPTION
       "Webdocs upgrade completed"
::= { notifications 1718 }

webdocsUpgradeFailed NOTIFICATION-TYPE
    OBJECTS{
        notificationDescription,
        notificationTime,
        notificationSeverity,
        notificationComponentName,
        notificationTargetEntityName,
        notificationEventCode
    }
    STATUS current
    DESCRIPTION
       "Webdocs upgrade failed"
::= { notifications 1719 }


-- Replication events
replicationTargetDeleted NOTIFICATION-TYPE
    OBJECTS{
        notificationDescription,
        notificationTime,
        notificationSeverity,
        notificationComponentName,
        notificationTargetEntityName,
        notificationEventCode
    }
    STATUS current
    DESCRIPTION
       "Replication target deleted"
::= { notifications 1801 }

replicationComplete NOTIFICATION-TYPE
    OBJECTS{
        notificationDescription,
        notificationTime,
        notificationSeverity,
        notificationComponentName,
        notificationTargetEntityName,
        notificationEventCode
    }
    STATUS current
    DESCRIPTION
       "Replication completed"
::= { notifications 1802 }

replicationAborted NOTIFICATION-TYPE
    OBJECTS{
        notificationDescription,
        notificationTime,
        notificationSeverity,
        notificationComponentName,
        notificationTargetEntityName,
        notificationEventCode
    }
    STATUS current
    DESCRIPTION
       "Replication aborted"
::= { notifications 1803 }

replicationAbandoned NOTIFICATION-TYPE
    OBJECTS{
        notificationDescription,
        notificationTime,
        notificationSeverity,
        notificationComponentName,
        notificationTargetEntityName,
        notificationEventCode
    }
    STATUS current
    DESCRIPTION
       "Replication abandoned"
::= { notifications 1804 }

replicationResumed NOTIFICATION-TYPE
    OBJECTS{
        notificationDescription,
        notificationTime,
        notificationSeverity,
        notificationComponentName,
        notificationTargetEntityName,
        notificationEventCode
    }
    STATUS current
    DESCRIPTION
       "Replication resumed"
::= { notifications 1805 }

replicationStarted NOTIFICATION-TYPE
    OBJECTS{
        notificationDescription,
        notificationTime,
        notificationSeverity,
        notificationComponentName,
        notificationTargetEntityName,
        notificationEventCode
    }
    STATUS current
    DESCRIPTION
       "Replication started"
::= { notifications 1806 }

replicationFailed NOTIFICATION-TYPE
    OBJECTS{
        notificationDescription,
        notificationTime,
        notificationSeverity,
        notificationComponentName,
        notificationTargetEntityName,
        notificationEventCode
    }
    STATUS current
    DESCRIPTION
       "Replication failed"
::= { notifications 1807 }

replicationSourceRegistered NOTIFICATION-TYPE
    OBJECTS{
        notificationDescription,
        notificationTime,
        notificationSeverity,
        notificationComponentName,
        notificationTargetEntityName,
        notificationEventCode
    }
    STATUS current
    DESCRIPTION
       "Replication source registered"
::= { notifications 1808 }

replicationPaused NOTIFICATION-TYPE
    OBJECTS{
        notificationDescription,
        notificationTime,
        notificationSeverity,
        notificationComponentName,
        notificationTargetEntityName,
        notificationEventCode
    }
    STATUS current
    DESCRIPTION
       "Replication paused"
::= { notifications 1809 }

-- System services events
snmpServiceStarted NOTIFICATION-TYPE
    OBJECTS{
        notificationDescription,
        notificationTime,
        notificationSeverity,
        notificationComponentName,
        notificationTargetEntityName,
        notificationEventCode
    }
    STATUS current
    DESCRIPTION
       "SNMP Service started"
::= { notifications 1901 }

snmpServiceStartFailed NOTIFICATION-TYPE
    OBJECTS{
        notificationDescription,
        notificationTime,
        notificationSeverity,
        notificationComponentName,
        notificationTargetEntityName,
        notificationEventCode
    }
    STATUS current
    DESCRIPTION
       "SNMP Service failed to start"
::= { notifications 1902 }

snmpServiceStopped NOTIFICATION-TYPE
    OBJECTS{
        notificationDescription,
        notificationTime,
        notificationSeverity,
        notificationComponentName,
        notificationTargetEntityName,
        notificationEventCode
    }
    STATUS current
    DESCRIPTION
       "SNMP Service stopped"
::= { notifications 1903 }

snmpServiceStopFailed NOTIFICATION-TYPE
    OBJECTS{
        notificationDescription,
        notificationTime,
        notificationSeverity,
        notificationComponentName,
        notificationTargetEntityName,
        notificationEventCode
    }
    STATUS current
    DESCRIPTION
       "SNMP Service failed to stop"
::= { notifications 1904 }

smisServiceStarted NOTIFICATION-TYPE
    OBJECTS{
        notificationDescription,
        notificationTime,
        notificationSeverity,
        notificationComponentName,
        notificationTargetEntityName,
        notificationEventCode
    }
    STATUS current
    DESCRIPTION
       "SMIS service started"
::= { notifications 1905 }

smisServiceStartFailed NOTIFICATION-TYPE
    OBJECTS{
        notificationDescription,
        notificationTime,
        notificationSeverity,
        notificationComponentName,
        notificationTargetEntityName,
        notificationEventCode
    }
    STATUS current
    DESCRIPTION
       "SMIS Service failed to start"
::= { notifications 1906 }

smisServiceStopped NOTIFICATION-TYPE
    OBJECTS{
        notificationDescription,
        notificationTime,
        notificationSeverity,
        notificationComponentName,
        notificationTargetEntityName,
        notificationEventCode
    }
    STATUS current
    DESCRIPTION
       "SMIS Service stopped"
::= { notifications 1907 }

smisServiceStopFailed NOTIFICATION-TYPE
    OBJECTS{
        notificationDescription,
        notificationTime,
        notificationSeverity,
        notificationComponentName,
        notificationTargetEntityName,
        notificationEventCode
    }
    STATUS current
    DESCRIPTION
       "SMIS Service failed to stop"
::= { notifications 1908 }

-- IPMI notifications
ipmiTemperature NOTIFICATION-TYPE
    OBJECTS{
        notificationDescription,
        notificationTime,
        notificationSeverity,
        notificationComponentName,
        notificationEventCode,
        notificationSensorAction,
        notificationSensorNumber,
        notificationSensorSuspect,
        notificationReadingTriggerValue,
        notificationThresholdTriggerValue,
        notificationReadingUnit
    }
    STATUS current
    DESCRIPTION
        "An IPMI event was raised related to array's Temperature."
::= { notifications 2001}

ipmiVoltage NOTIFICATION-TYPE
    OBJECTS{
        notificationDescription,
        notificationTime,
        notificationSeverity,
        notificationComponentName,
        notificationEventCode,
        notificationSensorAction,
        notificationSensorNumber,
        notificationSensorSuspect,
        notificationReadingTriggerValue,
        notificationThresholdTriggerValue,
        notificationReadingUnit
    }
    STATUS current
    DESCRIPTION
        "An IPMI event was raised related to array's Voltage."
::= { notifications 2002}

ipmiCurrent NOTIFICATION-TYPE
    OBJECTS{
        notificationDescription,
        notificationTime,
        notificationSeverity,
        notificationComponentName,
        notificationEventCode,
        notificationSensorAction,
        notificationSensorNumber,
        notificationSensorSuspect,
        notificationReadingTriggerValue,
        notificationThresholdTriggerValue,
        notificationReadingUnit
    }
    STATUS current
    DESCRIPTION
        "An IPMI event was raised related to array's Current."
::= { notifications 2003}

ipmiFan NOTIFICATION-TYPE
    OBJECTS{
        notificationDescription,
        notificationTime,
        notificationSeverity,
        notificationComponentName,
        notificationEventCode,
        notificationSensorAction,
        notificationSensorNumber,
        notificationSensorSuspect,
        notificationReadingTriggerValue,
        notificationThresholdTriggerValue,
        notificationReadingUnit
    }
    STATUS current
    DESCRIPTION
        "An IPMI event was raised related to array's Fans."
::= { notifications 2004}

ipmiPowerSupply NOTIFICATION-TYPE
    OBJECTS{
        notificationDescription,
        notificationTime,
        notificationSeverity,
        notificationComponentName,
        notificationEventCode,
        notificationSensorAction,
        notificationSensorNumber,
        notificationSensorSuspect
    }
    STATUS current
    DESCRIPTION
        "An IPMI event was raised related to array's Power Supply."
::= { notifications 2005}

ipmiMemory NOTIFICATION-TYPE
    OBJECTS{
        notificationDescription,
        notificationTime,
        notificationSeverity,
        notificationComponentName,
        notificationEventCode,
        notificationSensorAction,
        notificationSensorNumber,
        notificationSensorSuspect
    }
    STATUS current
    DESCRIPTION
        "A IPMI Memory error was detected."
::= { notifications 2006}

ipmiCriticalInterrupt NOTIFICATION-TYPE
    OBJECTS{
        notificationDescription,
        notificationTime,
        notificationSeverity,
        notificationComponentName,
        notificationEventCode,
        notificationSensorAction,
        notificationSensorNumber,
        notificationSensorSuspect
    }
    STATUS current
    DESCRIPTION
        "An IPMI Critical Interrupt was received."
::= { notifications 2007}

ipmiThreshold NOTIFICATION-TYPE
    OBJECTS{
        notificationDescription,
        notificationTime,
        notificationSeverity,
        notificationComponentName,
        notificationEventCode,
        notificationSensorAction,
        notificationSensorNumber,
        notificationSensorSuspect,
        notificationReadingTriggerValue,
        notificationThresholdTriggerValue,
        notificationReadingUnit
    }
    STATUS current
    DESCRIPTION
        "An IPMI Threshold event was generated."
::= { notifications 2008}

ipmiOther NOTIFICATION-TYPE
    OBJECTS{
        notificationDescription,
        notificationTime,
        notificationSeverity,
        notificationComponentName,
        notificationEventCode,
        notificationSensorAction,
        notificationSensorNumber,
        notificationSensorSuspect
    }
    STATUS current
    DESCRIPTION
        "An IPMI event was received."
::= { notifications 2009}

-- FM/Sensor events
memoryFailure NOTIFICATION-TYPE
    OBJECTS{
        notificationDescription,
        notificationTime,
        notificationSeverity,
        notificationComponentName,
        notificationTargetEntityName,
        notificationEventCode
    }
    STATUS current
    DESCRIPTION
       "Memory failure"
::= { notifications 2051 }

sensorFailureEvent NOTIFICATION-TYPE
    OBJECTS{
        notificationDescription,
        notificationTime,
        notificationSeverity,
        notificationComponentName,
        notificationTargetEntityName,
        notificationEventCode
    }
    STATUS current
    DESCRIPTION
       "Sensor failure"
::= { notifications 2052 }

unknownSensorEvent NOTIFICATION-TYPE
    OBJECTS{
        notificationDescription,
        notificationTime,
        notificationSeverity,
        notificationComponentName,
        notificationTargetEntityName,
        notificationEventCode
    }
    STATUS current
    DESCRIPTION
       "Unknown sensor event"
::= { notifications 2053 }

-- Networking notifications
networkIpmpGroupUp NOTIFICATION-TYPE
    OBJECTS{
        notificationDescription,
        notificationTime,
        notificationSeverity,
        notificationComponentName,
        notificationTargetEntityName,
        notificationEventCode
    }
    STATUS current
    DESCRIPTION
       "IPMP group is up."
::= { notifications 2201 }

networkIpmpGroupDown NOTIFICATION-TYPE
    OBJECTS{
        notificationDescription,
        notificationTime,
        notificationSeverity,
        notificationComponentName,
        notificationTargetEntityName,
        notificationEventCode
    }
    STATUS current
    DESCRIPTION
       "IPMP group is down."
::= { notifications 2202 }

networkIpmpMemberInterfaceAdded NOTIFICATION-TYPE
    OBJECTS{
        notificationDescription,
        notificationTime,
        notificationSeverity,
        notificationComponentName,
        notificationTargetEntityName,
        notificationEventCode
    }
    STATUS current
    DESCRIPTION
       "Network interface added to IPMP group."
::= { notifications 2203 }

networkIpmpMemberInterfaceRemoved NOTIFICATION-TYPE
    OBJECTS{
        notificationDescription,
        notificationTime,
        notificationSeverity,
        notificationComponentName,
        notificationTargetEntityName,
        notificationEventCode
    }
    STATUS current
    DESCRIPTION
       "Network interface removed from IPMP group."
::= { notifications 2204 }

networkInterfaceUp NOTIFICATION-TYPE
    OBJECTS{
        notificationDescription,
        notificationTime,
        notificationSeverity,
        notificationComponentName,
        notificationTargetEntityName,
        notificationEventCode
    }
    STATUS current
    DESCRIPTION
       "Network interface is up."
::= { notifications 2205 }

networkInterfaceDown NOTIFICATION-TYPE
    OBJECTS{
        notificationDescription,
        notificationTime,
        notificationSeverity,
        notificationComponentName,
        notificationTargetEntityName,
        notificationEventCode
    }
    STATUS current
    DESCRIPTION
       "Network interface is down."
::= { notifications 2206 }

networkIpmpMemberLinkAggregateAdded NOTIFICATION-TYPE
    OBJECTS{
        notificationDescription,
        notificationTime,
        notificationSeverity,
        notificationComponentName,
        notificationTargetEntityName,
        notificationEventCode
    }
    STATUS current
    DESCRIPTION
       "Network link aggregate added to IPMP group."
::= { notifications 2207 }

networkIpmpMemberLinkAggregateRemoved NOTIFICATION-TYPE
    OBJECTS{
        notificationDescription,
        notificationTime,
        notificationSeverity,
        notificationComponentName,
        notificationTargetEntityName,
        notificationEventCode
    }
    STATUS current
    DESCRIPTION
       "Network link aggregate removed from IPMP group."
::= { notifications 2208 }

networkLinkAggregateCreated NOTIFICATION-TYPE
    OBJECTS{
        notificationDescription,
        notificationTime,
        notificationSeverity,
        notificationComponentName,
        notificationTargetEntityName,
        notificationEventCode
    }
    STATUS current
    DESCRIPTION
       "Network Link Aggregate is created successfully."
::= { notifications 2209 }

networkLinkAggregateDeleted NOTIFICATION-TYPE
    OBJECTS{
        notificationDescription,
        notificationTime,
        notificationSeverity,
        notificationComponentName,
        notificationTargetEntityName,
        notificationEventCode
    }
    STATUS current
    DESCRIPTION
       "Network Link Aggregate is deleted successfully."
::= { notifications 2210 }

clusterInterconnectUp NOTIFICATION-TYPE
    OBJECTS{
        notificationDescription,
        notificationTime,
        notificationSeverity,
        notificationComponentName,
        notificationTargetEntityName,
        notificationEventCode
    }
    STATUS current
    DESCRIPTION
       "Cluster interconnect is now up."
::= { notifications 2211 }

clusterInterconnectDown NOTIFICATION-TYPE
    OBJECTS{
        notificationDescription,
        notificationTime,
        notificationSeverity,
        notificationComponentName,
        notificationTargetEntityName,
        notificationEventCode
    }
    STATUS current
    DESCRIPTION
       "Cluster interconnect is down."
::= { notifications 2212 }

networkLinkAggregateModified NOTIFICATION-TYPE
    OBJECTS{
        notificationDescription,
        notificationTime,
        notificationSeverity,
        notificationComponentName,
        notificationTargetEntityName,
        notificationEventCode
    }
    STATUS current
    DESCRIPTION
       "Network link aggregate is modified."
::= { notifications 2213 }

networkIpmpGroupCreated NOTIFICATION-TYPE
    OBJECTS{
        notificationDescription,
        notificationTime,
        notificationSeverity,
        notificationComponentName,
        notificationTargetEntityName,
        notificationEventCode
    }
    STATUS current
    DESCRIPTION
       "Network interface group created."
::= { notifications 2214 }

networkIpmpGroupDeleted NOTIFICATION-TYPE
    OBJECTS{
        notificationDescription,
        notificationTime,
        notificationSeverity,
        notificationComponentName,
        notificationTargetEntityName,
        notificationEventCode
    }
    STATUS current
    DESCRIPTION
       "Network interface group deleted."
::= { notifications 2215 }

networkIpmpGroupModified NOTIFICATION-TYPE
    OBJECTS{
        notificationDescription,
        notificationTime,
        notificationSeverity,
        notificationComponentName,
        notificationTargetEntityName,
        notificationEventCode
    }
    STATUS current
    DESCRIPTION
       "Network interface group modified."
::= { notifications 2216 }

-- VMWare notifications
vmwareNFSDatastoreCreated NOTIFICATION-TYPE
    OBJECTS{
        notificationDescription,
        notificationTime,
        notificationSeverity,
        notificationComponentName,
        notificationTargetEntityName,
        notificationEventCode
    }
    STATUS current
    DESCRIPTION
       "VMWare NFS Datastore has been created."
::= { notifications 2301 }

vmwareNFSDatastoreDeleted NOTIFICATION-TYPE
    OBJECTS{
        notificationDescription,
        notificationTime,
        notificationSeverity,
        notificationComponentName,
        notificationTargetEntityName,
        notificationEventCode
    }
    STATUS current
    DESCRIPTION
       "VMWare NFS Datastore has been deleted."
::= { notifications 2302 }

-- NVDIMM notifications
nvdimmFailDeviceError NOTIFICATION-TYPE
    OBJECTS{
        notificationDescription,
        notificationTime,
        notificationSeverity,
        notificationComponentName,
        notificationTargetEntityName,
        notificationEventCode
    }
    STATUS current
    DESCRIPTION
       "NVDIMM Device is not detectable."
::= { notifications 2401 }

nvdimmFailSoftError NOTIFICATION-TYPE
    OBJECTS{
        notificationDescription,
        notificationTime,
        notificationSeverity,
        notificationComponentName,
        notificationTargetEntityName,
        notificationEventCode
    }
    STATUS current
    DESCRIPTION
       "NVDIMM Device has encountered some errors."
::= { notifications 2402 }

nvdimmFailInitializationError NOTIFICATION-TYPE
    OBJECTS{
        notificationDescription,
        notificationTime,
        notificationSeverity,
        notificationComponentName,
        notificationTargetEntityName,
        notificationEventCode
    }
    STATUS current
    DESCRIPTION
       "Failed to initialize NVDIMM Device."
::= { notifications 2403 }

nvdimmFailUnknownError NOTIFICATION-TYPE
    OBJECTS{
        notificationDescription,
        notificationTime,
        notificationSeverity,
        notificationComponentName,
        notificationTargetEntityName,
        notificationEventCode
    }
    STATUS current
    DESCRIPTION
       "NVDIMM failure encountered. Please see the IntelliFlash UI event details."
::= { notifications 2404 }

--
-- End of  notifications
--

tegileConformance OBJECT IDENTIFIER ::= { tegile 3 }

tegileGroups OBJECT IDENTIFIER ::= { tegileConformance 1 }

currentObjectGroup OBJECT-GROUP
    OBJECTS {
            arrayHostName,
            arrayManagementIP,
            arrayHardwareModel,
            arraySoftwareVersion,
            arrayGUID,
            haControllerA-Name,
            haControllerA-IPAddr,
            haControllerA-Uptime,
            haControllerB-Name,
            haControllerB-IPAddr,
            haControllerB-Uptime,
            snmpAgentVersion,
            cpuTotalUsage,
            cpuSystemCalls,
            cpuInterrupts,
            cacheTotalWriteMbps,
            cacheTotalReadMbps,
            cacheTotalWriteIops,
            cacheTotalReadIops,
            cacheRAMReads,
            cacheSSDReads,
            diskTotalWriteMbps,
            diskTotalReadMbps,
            diskTotalWriteIops,
            diskTotalReadIops,
            diskDataWriteMbps,
            diskDataReadMbps,
            diskDataWriteIops,
            diskDataReadIops,
            diskAvgWriteLatency,
            diskAvgReadLatency,
            diskIOCount,
            diskRandomIOCount,
            diskSequentialIOCount,
            poolTotalWriteMbps,
            poolTotalReadMbps,
            poolTotalWriteIops,
            poolTotalReadIops,
            poolAvgWriteLatency,
            poolAvgReadLatency,
            cifsTotalWriteMBps,
            cifsTotalReadMBps,
            cifsTotalWriteIops,
            cifsTotalReadIops,
            cifsAvgWriteLatency,
            cifsAvgReadLatency,
            nfsTotalWriteMBps,
            nfsTotalReadMBps,
            nfsTotalWriteIops,
            nfsTotalReadIops,
            nfsAvgWriteLatency,
            nfsAvgReadLatency,
            iscsiTotalWriteMBps,
            iscsiTotalReadMBps,
            iscsiWriteIops,
            iscsiTotalReadIops,
            iscsiAvgWriteLatency,
            iscsiAvgReadLatency,
            fcTotalWriteMBps,
            fcTotalReadMBps,
            fcTotalWriteIops,
            fcTotalReadIops,
            fcAvgWriteLatency,
            fcAvgReadLatency,
            vmwareNFSDatastoresTotalWriteMBps,
            vmwareNFSDatastoresTotalReadMBps,
            vmwareNFSDatastoresTotalWriteIops,
            vmwareNFSDatastoresTotalReadIops,
            vmwareNFSDatastoresAvgWriteLatency,
            vmwareNFSDatastoresAvgReadLatency,
            networkTotalReceiveMbps,
            networkTotalTransmitMbps,
            hypervSMBVMsTotalWriteMBps,
            hypervSMBVMsTotalReadMBps,
            hypervSMBVMsTotalWriteIops,
            hypervSMBVMsTotalReadIops,
            hypervSMBVMsAvgWriteLatency,
            hypervSMBVMsAvgReadLatency,
            diskCount,
            diskAlias,
            diskSize,
            diskState,
            diskType,
            diskPoolName,
            poolCount,
            poolName,
            poolState,
            poolHealth,
            poolOwnerController,
            poolProjectCount,
            poolSize,
            poolUsedSize,
            poolFreeSize,
            poolDataSize,
            poolPostDedupDataSize,
            poolPostCompressionDataSize,
            poolUnusedReservedSize,
            poolTotalSaving,
            poolDataWriteMbps,
            poolDataReadMbps,
            poolDataWriteIops,
            poolDataReadIops,
            poolDataWriteLatency,
            poolDataReadLatency,
            poolIFlashWriteMbps,
            poolIFlashReadMbps,
            poolIFlashWriteIops,
            poolIFlashReadIops,
            poolIFlashWriteLatency,
            poolIFlashReadLatency,
            poolCacheWriteMbps,
            poolCacheReadMbps,
            poolCacheWriteIops,
            poolCacheReadIops,
            poolCacheWriteLatency,
            poolCacheReadLatency,
            poolMetaWriteMbps,
            poolMetaReadMbps,
            poolMetaWriteIops,
            poolMetaReadIops,
            poolMetaWriteLatency,
            poolMetaReadLatency,
            projectName,
            projectPoolName,
            projectDedupEnabled,
            projectCompressionEnabled,
            projectQuotaSize,
            projectDataSize,
            projectFreeSize,
            projectSnapshotSize,
            projectPostCompressionDataSize,
            projectUnusedReservedSize,
            projectTotalSaving,
            projectLunCount,
            projectShareCount,
            lunName,
            lunProjectName,
            lunPoolName,
            lunGUID,
            lunBlockSize,
            lunDedupEnabled,
            lunCompressionEnabled,
            lunSize,
            lunDataSize,
            lunSnapshotSize,
            lunFreeSize,
            lunReservedSize,
            lunCompressedRatio,
            lunProtocol,
            lunTargetGroup,
            lunInitiatorGroup,
            lunWriteMBps,
            lunReadMBps,
            lunWriteIops,
            lunReadIops,
            lunWriteLatency,
            lunReadLatency,
            shareName,
            shareMountPoint,
            shareProjectName,
            sharePoolName,
            shareQuota,
            shareNFSEnabled,
            shareCIFSEnabled,
            shareDedupEnabled,
            shareCompressionEnabled,
            shareDataSize,
            shareSnapshotSize,
            shareReservedSize,
            shareCompressedRatio,
            shareCIFSWriteMBps,
            shareCIFSReadMBps,
            shareCIFSWriteIops,
            shareCIFSReadIops,
            shareCIFSWriteLatency,
            shareCIFSReadLatency,
            shareNFSWriteMBps,
            shareNFSReadMBps,
            shareNFSWriteIops,
            shareNFSReadIops,
            shareNFSWriteLatency,
            shareNFSReadLatency,
            iscsiTargetName,
            iscsiTargetAlias,
            iscsiTargetGroup,
            iscsiTargetAuth,
            iscsiTargetWriteMBps,
            iscsiTargetReadMBps,
            iscsiTargetWriteIops,
            iscsiTargetReadIops,
            iscsiTargetWriteLatency,
            iscsiTargetReadLatency,
            iscsiInitiatorName,
            iscsiInitiatorChapUser,
            iscsiInitiatorGroup,
            fcTargetName,
            fcTargetStatus,
            fcTargetGroup,
            fcTargetCurrentSpeed,
            fcTargetWriteMBps,
            fcTargetReadMBps,
            fcTargetWriteIops,
            fcTargetReadIops,
            fcTargetWriteLatency,
            fcTargetReadLatency,
            fcInitiatorName,
            fcInitiatorGroup,
            vmwareNFSDatastoreVMName,
            vmwareNFSDatastoreESXName,
            vmwareNFSDatastorePoolName,
            vmwareNFSDatastoreWriteMBps,
            vmwareNFSDatastoreReadMBps,
            vmwareNFSDatastoreWriteIops,
            vmwareNFSDatastoreReadIops,
            vmwareNFSDatastoreWriteLatency,
            vmwareNFSDatastoreReadLatency,
            hypervSMBVMName,
            hypervSMBHyperVName,
            hypervSMBVMPoolName,
            hypervSMBVMWriteMBps,
            hypervSMBVMReadMBps,
            hypervSMBVMWriteIops,
            hypervSMBVMReadIops,
            hypervSMBVMWriteLatency,
            hypervSMBVMReadLatency,
            haResourceName,
            haResourceDescription,
            haResourceStatus,
            haResourceGroup,
            haResourceActiveNode,
            nicName,
            nicState,
            nicGroup,
            nicMTU,
            nicReceiveMbps,
            nicTransmitMbps,
            linkAggregateGroupName,
            linkAggregatePorts,
            linkAggregateOutboundPolicy,
            linkAggregateMode,
            linkAggregateMTU,
            interfaceGroupName,
            interfaceGroupVLAN,
            interfaceGroupState,
            mappedInterfaceName,
            mappedInterfaceType,
            mappedInterfaceGroup,
            physicalInterfaceAddress,
            physicalInterfaceNetmask,
            physicalInterfaceType,
            physicalInterfaceActiveOn,
            physicalInterfaceFailoverMode,
            physicalInterfaceGroup,
            notificationDescription,
            notificationTime,
            notificationSeverity,
            notificationComponentName,
            notificationTargetEntityName,
            notificationEventCode,
            notificationSensorAction,
            notificationSensorNumber,
            notificationSensorSuspect,
            notificationReadingTriggerValue,
            notificationThresholdTriggerValue,
            notificationReadingUnit
    }
    STATUS obsolete
    DESCRIPTION
        "This used to be the collection of objects that represented all the 
        information Tegile Array provided through SNMP.
        In IntelliFlash 3.7.1.0, this group has been made obsolete."
    ::= { tegileGroups 1 }

currentNotificationGroup NOTIFICATION-GROUP
    NOTIFICATIONS {
            testNotification,
            diskIsOnline,
            diskGoneOffline,
            diskError,
            spareDiskReplaced,
            diskSlowIo,
            poolDiskReplaced,
            poolCreated,
            poolDeleted,
            poolDeletionFailed,
            poolExpanded,
            poolExported,
            poolImported,
            poolUpgraded,
            poolQuotaExceedThresholdWarning,
            poolMetaDataQuotaExceedThresholdWarning,
            poolAvailableMetaToDataRatioBelowThresholdWarning,
            poolQuotaFinished,
            poolDegraded,
            projectCreatedSuccessfully,
            projectDeletionFailed,
            projectDeleted,
            projectModified,
            projectThresholdExceedWarning,
            projectQuotaFinished,
            projectCreatedWithNonOptimalBlockSize,
            volumeCreatedSuccessfully,
            volumeModifyCompleted,
            volumeDeleteCompleted,
            volumeDeleteFailed,
            volumeExceedsThresholdWarning,
            volumeQuotaFinished,
            volumeCreatedWithNonOptimalBlockSize,
            volumeOnline,
            volumeOffline,
            shareCreatedSuccessfully,
            shareDeletionFailed,
            shareDeleted,
            shareExceedThresholdWarning,
            shareQuotaFinished,
            shareCreatedWithNonOptimalBlockSize,
            aclMigrationStarted,
            aclMigrationCompleted,
            deleteFolderCompleted,
            deleteFolderFailed,
            snapshotCreatedSuccessfully,
            snapshotCreationFailed,
            snapshotDeletedSuccessfully,
            snapshotDeleteFailed,
            snapshotCloningFailed,
            snapshotCloneCompleted,
            snapshotRollbackFailed,
            snapshotRollbackCompleted,
            haResourceGroupTakeBackCompleted,
            haResourceGroupTakeOverCompleted,
            controllerUp,
            controllerDown,
            intelliFlashSoftwareUp,
            intelliFlashSoftwareDown,
            controllerTimeDrift,
            fcInitiatorCreateCompleted,
            fcInitiatorCreateFailed,
            fcTargetResetHbaPortCompleted,
            fcTargetResetHbaPortFailed,
            fcPortOnline,
            fcPortOffline,
            initiatorGroupCreateCompleted,
            initiatorGroupMemberAdded,
            initiatorGroupMemberRemoved,
            initiatorGroupDeleteCompleted,
            iscsiInitiatorCreateCompleted,
            iscsiInitiatorCreateFailed,
            iscsiInitiatorModifyCompleted,
            iscsiInitiatorDeleteCompleted,
            iscsiTargetCreateCompleted,
            iscsiTargetModifyCompleted,
            iscsiTargetDeleteCompleted,
            iscsiTargetError,
            iscsiTargetGroupError,
            iscsiImproperTargetGroup,
            targetGroupCreateCompleted,
            targetGroupMemberAdded,
            targetGroupMemberRemoved,
            targetGroupDeleteCompleted,
            adServerTimeDrift,
            maintenanceModeEnabled,
            maintenanceModeDisabled,
            diagnosticDataUploaded,
            diagnosticDataUploadingFailed,
            alertsCleanupCompleted,
            dnsServersUnreachable,
            allDnsServersUnreachable,
            userLoginFailed,
            ntpServerTimeDrift,
            intellishellSessionStarted,
            intellishellSessionEnded,
            smbSocketFailure,
            netbiosSocketFailure,
            upgradeStarted,
            upgradeCompleted,
            upgradeFailed,
            upgradeTimeout,
            upgradeCantProcessFilesManually,
            upgradeDownloadStarted,
            upgradeDownloadCompleted,
            upgradeDownloadFailed,
            tdpsUpgradeCompleted,
            tdpsUpgradeFailed,
            tdpsUpgradeTimeout,
            tdpsUpgradeDownloadStarted,
            tdpsUpgradeDownloadCompleted,
            tdpsUpgradeDownloadFailed,
            webdocsUpgradeDownloadStarted,
            webdocsUpgradeDownloadCompleted,
            webdocsUpgradeDownloadFailed,
            webdocsUpgradeCompleted,
            webdocsUpgradeFailed,
            replicationTargetDeleted,
            replicationComplete,
            replicationAborted,
            replicationAbandoned,
            replicationResumed,
            replicationStarted,
            replicationFailed,
            replicationSourceRegistered,
            replicationPaused,
            snmpServiceStarted,
            snmpServiceStartFailed,
            snmpServiceStopped,
            snmpServiceStopFailed,
            smisServiceStarted,
            smisServiceStartFailed,
            smisServiceStopped,
            smisServiceStopFailed,
            ipmiTemperature,
            ipmiVoltage,
            ipmiCurrent,
            ipmiFan,
            ipmiPowerSupply,
            ipmiMemory,
            ipmiCriticalInterrupt,
            ipmiThreshold,
            ipmiOther,
            memoryFailure,
            sensorFailureEvent,
            unknownSensorEvent,
            networkIpmpGroupUp,
            networkIpmpGroupDown,
            networkIpmpMemberInterfaceAdded,
            networkIpmpMemberInterfaceRemoved,
            networkIpmpMemberLinkAggregateAdded,
            networkIpmpMemberLinkAggregateRemoved,
            networkLinkAggregateCreated,
            networkLinkAggregateDeleted,
            clusterInterconnectUp,
            clusterInterconnectDown,
            networkLinkAggregateModified,
            networkInterfaceUp,
            networkInterfaceDown,
            networkIpmpGroupCreated,
            networkIpmpGroupDeleted,
            networkIpmpGroupModified,
            vmwareNFSDatastoreCreated,
            vmwareNFSDatastoreDeleted,
            nvdimmFailDeviceError,
            nvdimmFailSoftError,
            nvdimmFailInitializationError,
            nvdimmFailUnknownError
    }
    STATUS current
    DESCRIPTION
        "Collection of the notifications raised by Tegile SNMP Agent."
    ::= { tegileGroups 2 }

arrayInfoGroup OBJECT-GROUP
    OBJECTS {
            arrayHostName,
            arrayManagementIP,
            arrayHardwareModel,
            arraySoftwareVersion,
            arrayGUID,
            haControllerA-Name,
            haControllerA-IPAddr,
            haControllerA-Uptime,
            haControllerB-Name,
            haControllerB-IPAddr,
            haControllerB-Uptime,
            snmpAgentVersion
    }
    STATUS current
    DESCRIPTION
        "Collection of objects for getting information about the Array."
    ::= { tegileGroups 3 }

globalStatisticsGroup OBJECT-GROUP
    OBJECTS {
            cpuTotalUsage,
            cpuSystemCalls,
            cpuInterrupts,
            cacheTotalWriteMbps,
            cacheTotalReadMbps,
            cacheTotalWriteIops,
            cacheTotalReadIops,
            cacheRAMReads,
            cacheSSDReads,
            diskTotalWriteMbps,
            diskTotalReadMbps,
            diskTotalWriteIops,
            diskTotalReadIops,
            diskDataWriteMbps,
            diskDataReadMbps,
            diskDataWriteIops,
            diskDataReadIops,
            diskAvgWriteLatency,
            diskAvgReadLatency,
            diskIOCount,
            diskRandomIOCount,
            diskSequentialIOCount,
            poolTotalWriteMbps,
            poolTotalReadMbps,
            poolTotalWriteIops,
            poolTotalReadIops,
            poolAvgWriteLatency,
            poolAvgReadLatency,
            cifsTotalWriteMBps,
            cifsTotalReadMBps,
            cifsTotalWriteIops,
            cifsTotalReadIops,
            cifsAvgWriteLatency,
            cifsAvgReadLatency,
            nfsTotalWriteMBps,
            nfsTotalReadMBps,
            nfsTotalWriteIops,
            nfsTotalReadIops,
            nfsAvgWriteLatency,
            nfsAvgReadLatency,
            iscsiTotalWriteMBps,
            iscsiTotalReadMBps,
            iscsiWriteIops,
            iscsiTotalReadIops,
            iscsiAvgWriteLatency,
            iscsiAvgReadLatency,
            fcTotalWriteMBps,
            fcTotalReadMBps,
            fcTotalWriteIops,
            fcTotalReadIops,
            fcAvgWriteLatency,
            fcAvgReadLatency,
            vmwareNFSDatastoresTotalWriteMBps,
            vmwareNFSDatastoresTotalReadMBps,
            vmwareNFSDatastoresTotalWriteIops,
            vmwareNFSDatastoresTotalReadIops,
            vmwareNFSDatastoresAvgWriteLatency,
            vmwareNFSDatastoresAvgReadLatency,
            networkTotalReceiveMbps,
            networkTotalTransmitMbps,
            hypervSMBVMsTotalWriteMBps,
            hypervSMBVMsTotalReadMBps,
            hypervSMBVMsTotalWriteIops,
            hypervSMBVMsTotalReadIops,
            hypervSMBVMsAvgWriteLatency,
            hypervSMBVMsAvgReadLatency
    }
    STATUS current
    DESCRIPTION
        "Collection of objects for getting Array's global analytics data."
    ::= { tegileGroups 4 }

disksInfoGroup OBJECT-GROUP
    OBJECTS {
            diskCount,
            diskAlias,
            diskSize,
            diskState,
            diskType,
            diskPoolName
    }
    STATUS current
    DESCRIPTION
        "Collection of objects for getting Disks information."
    ::= { tegileGroups 5 }
    
poolObjectGroup OBJECT-GROUP
    OBJECTS {
            poolCount,
            poolName,
            poolState,
            poolHealth,
            poolOwnerController,
            poolProjectCount,
            poolSize,
            poolUsedSize,
            poolFreeSize,
            poolDataSize,
            poolPostDedupDataSize,
            poolPostCompressionDataSize,
            poolUnusedReservedSize,
            poolTotalSaving,
            poolDataWriteMbps,
            poolDataReadMbps,
            poolDataWriteIops,
            poolDataReadIops,
            poolDataWriteLatency,
            poolDataReadLatency,
            poolIFlashWriteMbps,
            poolIFlashReadMbps,
            poolIFlashWriteIops,
            poolIFlashReadIops,
            poolIFlashWriteLatency,
            poolIFlashReadLatency,
            poolCacheWriteMbps,
            poolCacheReadMbps,
            poolCacheWriteIops,
            poolCacheReadIops,
            poolCacheWriteLatency,
            poolCacheReadLatency,
            poolMetaWriteMbps,
            poolMetaReadMbps,
            poolMetaWriteIops,
            poolMetaReadIops,
            poolMetaWriteLatency,
            poolMetaReadLatency
    }
    STATUS current
    DESCRIPTION
        "Collection of objects for getting Pools related information."
    ::= { tegileGroups 6 }

projectObjectGroup OBJECT-GROUP
    OBJECTS {
            projectName,
            projectPoolName,
            projectDedupEnabled,
            projectCompressionEnabled,
            projectQuotaSize,
            projectDataSize,
            projectFreeSize,
            projectSnapshotSize,
            projectPostCompressionDataSize,
            projectUnusedReservedSize,
            projectTotalSaving,
            projectLunCount,
            projectShareCount
    }
    STATUS current
    DESCRIPTION
        "Collection of objects for getting Projects related information."
    ::= { tegileGroups 7 }

lunObjectGroup OBJECT-GROUP
    OBJECTS {
            lunName,
            lunProjectName,
            lunPoolName,
            lunGUID,
            lunBlockSize,
            lunDedupEnabled,
            lunCompressionEnabled,
            lunSize,
            lunDataSize,
            lunSnapshotSize,
            lunFreeSize,
            lunReservedSize,
            lunCompressedRatio,
            lunProtocol,
            lunTargetGroup,
            lunInitiatorGroup,
            lunWriteMBps,
            lunReadMBps,
            lunWriteIops,
            lunReadIops,
            lunWriteLatency,
            lunReadLatency
    }
    STATUS current
    DESCRIPTION
        "Collection of objects for getting LUNs related information."
    ::= { tegileGroups 8 }

shareObjectGroup OBJECT-GROUP
    OBJECTS {
            shareName,
            shareMountPoint,
            shareProjectName,
            sharePoolName,
            shareQuota,
            shareNFSEnabled,
            shareCIFSEnabled,
            shareDedupEnabled,
            shareCompressionEnabled,
            shareDataSize,
            shareSnapshotSize,
            shareReservedSize,
            shareCompressedRatio,
            shareCIFSWriteMBps,
            shareCIFSReadMBps,
            shareCIFSWriteIops,
            shareCIFSReadIops,
            shareCIFSWriteLatency,
            shareCIFSReadLatency,
            shareNFSWriteMBps,
            shareNFSReadMBps,
            shareNFSWriteIops,
            shareNFSReadIops,
            shareNFSWriteLatency,
            shareNFSReadLatency
    }
    STATUS current
    DESCRIPTION
        "Collection of objects for getting Shares related information."
    ::= { tegileGroups 9 }

sanObjectGroup OBJECT-GROUP
    OBJECTS {
            iscsiTargetName,
            iscsiTargetAlias,
            iscsiTargetGroup,
            iscsiTargetAuth,
            iscsiTargetWriteMBps,
            iscsiTargetReadMBps,
            iscsiTargetWriteIops,
            iscsiTargetReadIops,
            iscsiTargetWriteLatency,
            iscsiTargetReadLatency,
            iscsiInitiatorName,
            iscsiInitiatorChapUser,
            iscsiInitiatorGroup,
            fcTargetName,
            fcTargetStatus,
            fcTargetGroup,
            fcTargetCurrentSpeed,
            fcTargetWriteMBps,
            fcTargetReadMBps,
            fcTargetWriteIops,
            fcTargetReadIops,
            fcTargetWriteLatency,
            fcTargetReadLatency,
            fcInitiatorName,
            fcInitiatorGroup
    }
    STATUS current
    DESCRIPTION
        "Collection of objects for getting SAN related information."
    ::= { tegileGroups 10 }

vmObjectGroup OBJECT-GROUP
    OBJECTS {
            vmwareNFSDatastoreVMName,
            vmwareNFSDatastoreESXName,
            vmwareNFSDatastorePoolName,
            vmwareNFSDatastoreWriteMBps,
            vmwareNFSDatastoreReadMBps,
            vmwareNFSDatastoreWriteIops,
            vmwareNFSDatastoreReadIops,
            vmwareNFSDatastoreWriteLatency,
            vmwareNFSDatastoreReadLatency,
            hypervSMBVMName,
            hypervSMBHyperVName,
            hypervSMBVMPoolName,
            hypervSMBVMWriteMBps,
            hypervSMBVMReadMBps,
            hypervSMBVMWriteIops,
            hypervSMBVMReadIops,
            hypervSMBVMWriteLatency,
            hypervSMBVMReadLatency
    }
    STATUS current
    DESCRIPTION
        "Collection of objects for getting VMs related information."
    ::= { tegileGroups 11 }

haResourceObjectGroup OBJECT-GROUP
    OBJECTS {
            haResourceName,
            haResourceDescription,
            haResourceStatus,
            haResourceGroup,
            haResourceActiveNode
    }
    STATUS current
    DESCRIPTION
        "Collection of objects for getting HA Resources related information."
    ::= { tegileGroups 12 }

networkObjectGroup OBJECT-GROUP
    OBJECTS {
            nicName,
            nicState,
            nicGroup,
            nicMTU,
            nicReceiveMbps,
            nicTransmitMbps,
            linkAggregateGroupName,
            linkAggregatePorts,
            linkAggregateOutboundPolicy,
            linkAggregateMode,
            linkAggregateMTU,
            interfaceGroupName,
            interfaceGroupVLAN,
            interfaceGroupState,
            mappedInterfaceName,
            mappedInterfaceType,
            mappedInterfaceGroup,
            physicalInterfaceAddress,
            physicalInterfaceNetmask,
            physicalInterfaceType,
            physicalInterfaceActiveOn,
            physicalInterfaceFailoverMode,
            physicalInterfaceGroup
    }
    STATUS current
    DESCRIPTION
        "Collection of objects for getting Network related information."
    ::= { tegileGroups 13 }

notificationObjectGroup OBJECT-GROUP
    OBJECTS {
            notificationDescription,
            notificationTime,
            notificationSeverity,
            notificationComponentName,
            notificationTargetEntityName,
            notificationEventCode,
            notificationSensorAction,
            notificationSensorNumber,
            notificationSensorSuspect,
            notificationReadingTriggerValue,
            notificationThresholdTriggerValue,
            notificationReadingUnit
    }
    STATUS current
    DESCRIPTION
        "Collection of objects for representing notifications."
    ::= { tegileGroups 14 }

ifa3710NotificationGroup NOTIFICATION-GROUP
    NOTIFICATIONS {
            shareModified
    }
    STATUS current
    DESCRIPTION
        "Notifications added in 3.7.1.0"
    ::= { tegileGroups 15 }

tegileCompliances OBJECT IDENTIFIER ::= { tegileConformance 2 }

basicCompliance MODULE-COMPLIANCE
    STATUS obsolete
    DESCRIPTION
        "TEGILE-MIB MODULE-COMPLIANCE."
    MODULE -- this module
        MANDATORY-GROUPS { currentObjectGroup }
    ::= { tegileCompliances 1 }

basicCompliance1 MODULE-COMPLIANCE
    STATUS current
    DESCRIPTION
        "TEGILE-MIB MODULE-COMPLIANCE."
    MODULE -- this module
        MANDATORY-GROUPS { arrayInfoGroup, 
                           globalStatisticsGroup, 
                           disksInfoGroup, 
                           poolObjectGroup, 
                           projectObjectGroup, 
                           lunObjectGroup, 
                           shareObjectGroup, 
                           sanObjectGroup, 
                           vmObjectGroup, 
                           haResourceObjectGroup, 
                           networkObjectGroup, 
                           notificationObjectGroup,
                           currentNotificationGroup,
                           ifa3710NotificationGroup
    }
    ::= { tegileCompliances 2 }

END
